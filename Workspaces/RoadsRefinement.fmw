FME workspace RoadsRefinement.fmw
Title: RoadRefinement
Description: This is a implementation of the methodology presented in the thesis:
    "Semantic-based Geometry Refinement of 3D City Models for Testing Automated Driving"
    Study case:
    Roads
    Before running check Published Parameters to fine-tune expected results!
History: 09.08.2020,OlafWysocki,FirstPublication

Parameters:
- SourceDataset_LAS = ""C:\MasterThesis\RawData\3DMappingSolutions\Only_AreaOfInterests\LAS.las" "C:\MasterThesis\RawData\3DMappingSolutions\Only_AreaOfInterests\LAS_1.las" "C:\MasterThesis\RawData\3DMappingSolutions\Only_AreaOfInterests\LAS_2.las" "C:\MasterThesis\RawData\3DMappingSolutions\Only_AreaOfInterests\LAS_3.las" "C:\MasterThesis\RawData\3DMappingSolutions\Only_AreaOfInterests\LAS_4.las" "C:\MasterThesis\RawData\3DMappingSolutions\Only_AreaOfInterests\LAS_5.las" "C:\MasterThesis\RawData\3DMappingSolutions\Only_AreaOfInterests\LAS_6.las" "C:\MasterThesis\RawData\3DMappingSolutions\Only_AreaOfInterests\LAS_7.las" "C:\MasterThesis\RawData\3DMappingSolutions\Only_AreaOfInterests\LAS_8.las" "C:\MasterThesis\RawData\3DMappingSolutions\Only_AreaOfInterests\LAS_9.las" "C:\MasterThesis\RawData\3DMappingSolutions\Only_AreaOfInterests\LAS_10.las" "C:\MasterThesis\RawData\3DMappingSolutions\Only_AreaOfInterests\LAS_11.las" "C:\MasterThesis\RawData\3DMappingSolutions\Only_AreaOfInterests\LAS_12.las" "C:\MasterThesis\RawData\3DMappingSolutions\Only_AreaOfInterests\LAS_13.las" "C:\MasterThesis\RawData\3DMappingSolutions\Only_AreaOfInterests\LAS_14.las""   # Source ASPRS LAS File(s)
- FEATURE_TYPES =   # LAS Feature Types to Read
- SourceDataset_LAS_3 = ""C:\MasterThesis\RawData\LDBV\ALS\ShiftedALS\677_5403_all.las" "C:\MasterThesis\RawData\LDBV\ALS\ShiftedALS\677_5404_all.las" "C:\MasterThesis\RawData\LDBV\ALS\ShiftedALS\678_5403_all.las" "C:\MasterThesis\RawData\LDBV\ALS\ShiftedALS\678_5404_all.las""   # Source ASPRS LAS File(s)
- FEATURE_TYPES_2 =   # LAS Feature Types to Read
- DestDataset_CITYGML = C:\MasterThesis\Processing\CityGML\road.gml   # Destination CityGML Document
- RANGE_SLIDER = 8   # userOctreeDepth RANGE:[,] Please, provide octree depth
- RANGE_SLIDER = 0
- RANGE_SLIDER = 0.01
- autoClean = true   # Set up some cleaning to the process, like erasing unreferenced vertices, bad faces, etc.
- FILENAME_MUSTEXIST = C:\MasterThesis\Workbenches\MeshLabServer\Test.mlx   # XMLinput Config_mlx|*.mlx Select the configuration template file
- FILENAME = C:\MasterThesis\Workbenches\MeshLabServer\Config.mlx   # XMLOutput Config_mlx|*.mlx Select location to save the meshlab configuration file
- FILENAME_MUSTEXIST = C:\Software\VCG\MeshLab\meshlabserver.exe   # meshlabserver meshlabserver_exe|*.exe Select meshlabserver.exe file path
- tmpXYZ = C:\MasterThesis\Processing\IntermediatePointCloud_1\Road_1_xyz   # Select tmp folder for point clouds
- LASTOOL = C:\MasterThesis\Workbenches\LASTools\LAStools\bin\lasheight.exe   # Lasheight.exe location
- HEIGHTSTORAGESCALE = 10   # Height storage scaling (for "Store in user data" only)
- HEIGHTSTORAGE = -store_in_user_data
- SourceDataset_CITYGML = C:\MasterThesis\RawData\HDMap_as_CityGML\AreaOfInterestsOfLod3\Innestadt_areaOfLod3_road.gml   # Source CityGML File(s)
- ManholeCorrection = Yes   # Enforce manholes corrections?

Readers:
- LAS_1: LAS from $(SourceDataset_LAS)
- LAS_2: LAS from $(SourceDataset_LAS_3)
- CITYGML_1: CITYGML from $(SourceDataset_CITYGML)

Writers:
- CITYGML_2: CITYGML to $(DestDataset_CITYGML)

Note: General note: / This is a implementation of the methodology presented in the thesis: / "Semantic-based Geometry Refinement of 3D City Models for Testing Automated Driving"
Note: Study case: / Roads
Note: Before running check Published Parameters to fine-tune expected results!

Bookmark: 1.2: PointCloud MLS
LAS (reader LAS_1)
    -> CoordinateSystemSetter_3
CoordinateSystemSetter_3
    COORDSYS = EPSG:32632
    -> AttributeCreator
AttributeCreator
    ATTR_TABLE = SET_TO PointCloud = MLS
    -> Junction
Note: to clipper
Junction
    -> Junction_2

Bookmark: 2.1.3.1: Clipp ALS and MLS by buffers
Note: LAS MLS
Junction_2
    -> Clipper [CLIPPEE]
Note: LAS ALS
Junction_12
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttCleaner
AttCleaner: AttributeRemover
    LIST_ATTRS = citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href
    REMOVE_ATTRS = _clipped,citygml_appearance{0}.xlink_href,citygml_auxiliary_traffic_area{0}.xlink_href,citygml_class,citygml_class_codeSpace,citygml_creationDate,citygml_feature_role,citygml_feature_role_attr_name,citygml_feature_role_attr_val,citygml_function{0},citygml_function{0}.codeSpace,citygml_generalizes_to{0}.xlink_href,citygml_level_of_detail{0},citygml_relative_to_terrain,citygml_relative_to_water,citygml_target_uri,citygml_terminationDate,citygml_traffic_area{0}.xlink_href,citygml_usage{0},citygml_usage{0}.codeSpace,externalReference{0}.externalObject.name,externalReference{0}.externalObject.uri,externalReference{0}.informationSystem,fme_basename,gml_description,opendrive_laneSection_index,opendrive_laneSection_start,opendrive_lane_id,opendrive_lane_level,opendrive_lane_material_friction,opendrive_lane_material_roughness,opendrive_lane_material_surface,opendrive_lane_roadMark_color,opendrive_lane_roadMark_material,opendrive_lane_roadMark_type,opendrive_lane_roadMark_weight,opendrive_lane_speed_max,opendrive_lane_type,opendrive_roadObject_dynamic,opendrive_roadObject_id,opendrive_roadObject_name,opendrive_roadObject_orientation,opendrive_roadObject_type,opendrive_road_id,opendrive_road_junction,opendrive_road_length,opendrive_road_rule,LoD,_overlaps,fme_feature_type,minHeight,topHeight
    -> EnforceManholesCorrections

Bookmark: 1.2: PointCloud ALS
LAS (reader LAS_2)
    -> CoordinateSystemSetter_5
CoordinateSystemSetter_5
    COORDSYS = EPSG:32632
    -> AttributeCreator_2
AttributeCreator_2
    ATTR_TABLE = SET_TO PointCloud = ALS
    -> Junction_9
Note: to clipper
Junction_9
    -> Junction_12

Bookmark: 1.1: HDMapAsCityGML_noOffset -> LOD1/2
Building (reader CITYGML_1)
    attributes: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
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, opendrive_laneSection_index xml_buffer, opendrive_laneSection_start xml_buffer, opendrive_lane_id xml_buffer, opendrive_lane_level xml_buffer, opendrive_lane_material_friction xml_buffer, opendrive_lane_material_roughness xml_buffer,
      opendrive_lane_material_surface xml_buffer, opendrive_lane_roadMark_color xml_buffer, opendrive_lane_roadMark_material xml_buffer, opendrive_lane_roadMark_type xml_buffer, opendrive_lane_roadMark_weight xml_buffer, opendrive_lane_speed_max xml_buffer, opendrive_lane_type xml_buffer, opendrive_roadObject_dynamic xml_buffer, opendrive_roadObject_id xml_buffer, opendrive_roadObject_name xml_buffer, opendrive_roadObject_orientation xml_buffer, opendrive_roadObject_type xml_buffer, opendrive_road_id xml_buffer, opendrive_road_junction xml_buffer, opendrive_road_length xml_buffer, opendrive_road_rule xml_buffer
    -> CoordinateSystemSetter_8
CoordinateSystemSetter_8
    COORDSYS = EPSG:32632
    -> Junction_5
Note: go to SYSTEM
Junction_5
    -> Junction_6

Bookmark: 2.1.1: Preprocessing
Note: Roads
Junction_6
    -> setLoDAttribute
    -> TestFilter [off]

Bookmark: 2.1.1.1: Possible testing sides...
Note: TEMPORARY, for debugging road
TestFilter [off]
    DEFAULT_VALUE = rest
    TEST_LIST:
      "BOOL_OP,OR,COMPOSITE_TEST,""""""1 OR 2"""""",TEST_CLAUSE,TEST @Value(gml_id) = UUID_dd23fe76-d0b4-4759-962f-2e12024d77e3
      TEST @Value(gml_id) = UUID_0f3c7d0d-c83d-4d6f-b3f2-2d72863dd894",nyParkingSlot,"BOOL_OP,OR,COMPOSITE_TEST,""""""1 OR 2 OR 3"""""",TEST_CLAUSE,TEST @Value(gml_id) = UUID_b61d9a23-ea31-451c-ab22-98b2509e4905
      TEST @Value(gml_id) = UUID_660fcd1c-963d-41e8-a9b7-973bd6399b48
      TEST @Value(gml_id) = UUID_f0cd0e23-aef4-4cb7-af54-344e7612b098",garageHole,"BOOL_OP,OR,COMPOSITE_TEST,""""""1 OR 2"""""",TEST_CLAUSE,TEST @Value(gml_id) = UUID_e3ae747a-cac3-46db-9358-b408fee8238a
      TEST @Value(gml_id) = UUID_dbbdc207-b062-44c4-a680-2003f13039ec",byTheGate,"BOOL_OP,OR,COMPOSITE_TEST,""""""1"""""",TEST_CLAUSE,TEST @Value(gml_id) = UUID_b018b12a-6292-42a6-b5a7-a6a1f66f9686",byTheRedBuildingWithGarage,"BOOL_OP,OR,COMPOSITE_TEST,""""""1"""""",TEST_CLAUSE,TEST @Value(gml_id) = UUID_92828729-0c22-409f-971a-6c61ae4b4433",bikingLaneFirstBuilding
    nyParkingSlot -> setLoDAttribute [off]
    garageHole -> setLoDAttribute [off]
    byTheGate -> setLoDAttribute [off]
    byTheRedBuildingWithGarage -> setLoDAttribute [off]
    bikingLaneFirstBuilding -> setLoDAttribute [off]

Bookmark: 2.1.1.2: Extract and set attributes, assumptions
Note: create attribute instead of list for LoD
setLoDAttribute: AttributeCreator
    ATTR_TABLE = SET_TO LoD = @Value(citygml_level_of_detail{0})
    -> TopMinObjectsHeight
TopMinObjectsHeight: BoundsExtractor
    ZMAX = topHeight
    ZMIN = minHeight
    -> AddLODDepAccAttributes
Note: create attribute for later buffer (X,Y)/offset (Z) depending on LoD -> CityGML Enconding standards
AddLODDepAccAttributes: AttributeCreator
    ATTR_TABLE = SET_TO Accuracy = FME_CONDITIONAL:DEFAULT_VALUE'_FME_NO_OP_'BOOL_OP;OR;COMPOSITE_TEST;1;TEST @Value(LoD) = 1'5'BOOL_OP;OR;COMPOSITE_TEST;1;TEST @Value(LoD) = 2'2'BOOL_OP;OR;COMPOSITE_TEST;1;TEST @Value(LoD) = 3'0.5'BOOL_OP;OR;COMPOSITE_TEST;1;TEST @Value(LoD) = 4'0.2'FME_NUM_CONDITIONS5___
    -> PossibleHeightDevi
PossibleHeightDevi: AttributeCreator
    ATTR_TABLE:
      SET_TO PosMH = @Evaluate(@sub(@Value(minHeight),@Value(Accuracy)))
      SET_TO RelPosHeight = @sub(@Value(topHeight),@Value(PosMH))
      SET_TO RHeight = @sub(@Value(topHeight),@Value(minHeight))
    -> Type_Distributor

Bookmark: 2.1.1.3: Change buffer depending on type and LoD
Note: only segments for vehicles
Type_Distributor: TestFilter
    DEFAULT_VALUE = <UNFILTERED>
    TEST_LIST = "BOOL_OP,AND,COMPOSITE_TEST,""""""1"""""",TEST_CLAUSE,TEST @Value(opendrive_lane_type) = DRIVING",Road_Driving
    Road_Driving -> LoD_Distributor
LoD_Distributor: TestFilter
    DEFAULT_VALUE = <UNFILTERED>
    TEST_LIST = "BOOL_OP,OR,COMPOSITE_TEST,""""""1"""""",TEST_CLAUSE,TEST @Value(LoD) = 1",LoD1,"BOOL_OP,OR,COMPOSITE_TEST,""""""1"""""",TEST_CLAUSE,TEST @Value(LoD) = 2",LoD2,"BOOL_OP,OR,COMPOSITE_TEST,""""""1"""""",TEST_CLAUSE,TEST @Value(LoD) = 3",LoD3
    LoD1 -> SurfaceNormalExtractor
    LoD2 -> 2DForcer_3
    LoD3 -> 2DForcer_2

Bookmark: 2.1.2.1: Needed for LoD1 to find GroundSurface
SurfaceNormalExtractor
    -> GeometryPartExtractor
Note: select ground surface based on normals
GeometryPartExtractor
    GQUERY:
      for $geom in //geometry
      where fme:get-trait($geom, 'surface_normal_z')/number() < 0
      return number($geom/@fme_id)
    EXTRACTED -> Aggregator
Aggregator
    ACCUM_ATTRS_NAME = Use Attributes From One Feature
    AGGREGATE_TYPE = Homogeneous Collection (If Possible)
    GROUP_BY = gml_id
    MODE = Geometry - Assemble One Level
    SEP = ,
    AGGREGATE -> 2DForcer
2DForcer
    2D -> Junction_7

Bookmark: 2.1.2.2: Needed for LoD2 to find extent
2DForcer_3
    2D -> HullAccumulator_2
    2D -> AreaOnAreaOverlayer_2 [AREA]
HullAccumulator_2
    3DMODE_PARAM = 2D
    ACCUM_INPUT_ATTRS = Use Attributes From One Feature
    GROUP_BY = gml_id
    HULLTYPE_PARAM = Convex ()
    HULL -> AreaOnAreaOverlayer_2 [AREA]
Note: Filter out edges etc
AreaOnAreaOverlayer_2
    ACCUM_ATTRS_NAME = Use Attributes From One Feature
    CLEANING_TOLERANCE = Automatic
    CONNECT_Z_MODE = First Wins
    DEAGGREGATE_INPUT = Yes
    GROUP_BY = gml_id
    OVC_ATTR = _overlaps
    AREA -> Dissolver_2
Dissolver_2
    ACCUM_INPUT_ATTRS = Use Attributes From One Feature
    CLEANING_TOLERANCE = Automatic
    CONNECT_Z_MODE = First Wins
    DEAGGREGATE_INPUT = Yes
    GROUP_BY = gml_id
    AREA -> Junction_7

Bookmark: 2.1.2.3: Needed for LoD3 to find extent
2DForcer_2
    2D -> HullAccumulator
    2D -> AreaOnAreaOverlayer [AREA]
HullAccumulator
    3DMODE_PARAM = 2D
    ACCUM_INPUT_ATTRS = Use Attributes From One Feature
    GROUP_BY = gml_id
    HULLTYPE_PARAM = Convex ()
    HULL -> AreaOnAreaOverlayer [AREA]
Note: Filter out edges etc,
AreaOnAreaOverlayer
    ACCUM_ATTRS_NAME = Use Attributes From One Feature
    CLEANING_TOLERANCE = Automatic
    CONNECT_Z_MODE = First Wins
    DEAGGREGATE_INPUT = Yes
    GROUP_BY = gml_id
    OVC_ATTR = _overlaps
    AREA -> Dissolver
Dissolver
    ACCUM_INPUT_ATTRS = Use Attributes From One Feature
    CLEANING_TOLERANCE = Automatic
    CONNECT_Z_MODE = First Wins
    DEAGGREGATE_INPUT = Yes
    GROUP_BY = gml_id
    AREA -> Junction_7

Bookmark: 2.1.2: Buffer creation
Junction_7
    -> Respective_Accuracy2D_buffer
    -> Junction_10
Note: Add as apriori attributes to the writer
Junction_13
    -> Junction_14
Note: add to SR clipper
Junction_10
    -> Junction_11

Bookmark: 2.1.2.4: Accuracy buffer, 2D & 3D
Respective_Accuracy2D_buffer: Bufferer
    ANGLE = 22.5
    CAP_STYLE = None
    CORNER_STYLE = Arc
    MODE = AREA
    OFFSET = @Value(Accuracy)
    OFFSET_UNITS = NONE
    PRECISION = APPROX
    BUFFERED -> 3DForcer
3DForcer
    KEEPZVAL = No
    ZVALATTR = @Value(PosMH)
    -> Respective_Accuracy3D_buffer
Respective_Accuracy3D_buffer: Extruder
    DIRECTION = Vertical
    DISTANCE = @sum(@Value(RelPosHeight),@Value(Accuracy))
    EXTRUDED -> Clipper [CLIPPER]
    EXTRUDED -> Junction_13

Bookmark: 2.1.3.2: Based on param enforce or not corrections
EnforceManholesCorrections: TestFilter
    DEFAULT_VALUE = <UNFILTERED>
    TEST_LIST = "BOOL_OP,OR,COMPOSITE_TEST,""""""1"""""",TEST_CLAUSE,TEST $(ManholeCorrection) = Yes",Yes,"BOOL_OP,OR,COMPOSITE_TEST,""""""1"""""",TEST_CLAUSE,TEST $(ManholeCorrection) = No",No
    Yes -> TestFilter_2
    No -> ALS_MLScombiner
Note: only MLS to be rectified
TestFilter_2
    DEFAULT_VALUE = MLS
    TEST_LIST = "BOOL_OP,OR,COMPOSITE_TEST,""""""1"""""",TEST_CLAUSE,TEST @Value(PointCloud) = ALS",ALS
    ALS -> FeatureHolder
    MLS -> MLScombiner_2
FeatureHolder
    -> Junction_3
Note: ALS without changes goes further
Junction_3
    -> Junction_4

Bookmark: 2.1.3.4: Rallying point, merge again ALS with MLS
Note: ALS without changes
Junction_4
    -> ALS_MLScombiner
ALS_MLScombiner: PointCloudCombiner
    ACCUM_ATTRS_NAME = Yes
    EXTRACT_RASTER_NODATA_NAME = No
    GROUP_BY = gml_id
    SPACING = 1.0
    -> LAStools.lasground [PointCloud]

Bookmark: 2.1.3.3: Manholes corrections by filtering noise by height
MLScombiner_2: PointCloudCombiner
    ACCUM_ATTRS_NAME = Yes
    EXTRACT_RASTER_NODATA_NAME = No
    GROUP_BY = gml_id
    SPACING = 1.0
    -> Tiler
    -> Clipper_3 [CLIPPEE]
Note: to create local patches and calculate height there
Tiler
    BOUNDARY_CASES = No
    CLEANING_TOLERANCE = Automatic
    COL_ATTR = _column
    GROUP_BY = gml_id
    LINES_AS_SEGMENTS = No
    MEASURE_TYPE = Continuous
    MISSING_VAL_MODE = Compute
    ROW_ATTR = _row
    STARTINGCORNER = Lower Left
    TILING_TYPE = Tile Size
    XINC = 1
    YINC = 1
    TILED -> modeCalc
modeCalc: PointCloudStatisticsCalculator
    POINT_COMPONENTS = "z        MODE intensity        "
    -> AttributeCreator_3
Note: threshold 10cm
AttributeCreator_3
    ATTR_TABLE = SET_TO cutNoise = @sub(@Value(z.mode),0.10)
    -> BoundingBoxReplacer
BoundingBoxReplacer
    BOXTYPE = 2D Oriented Bounding Box
    BOX -> 3DForcer_2
Note: shift to low position to detect outliers
3DForcer_2
    KEEPZVAL = No
    ZVALATTR = @Value(cutNoise)
    -> Extruder
Note: extrude in NEGATIVE direction to minimize double clipping in further clipper
Extruder
    DIRECTION = Specified
    EXTRUSION_X = 0.0
    EXTRUSION_Y = 0.0
    EXTRUSION_Z = -1
    EXTRUDED -> Clipper_3 [CLIPPER]
Note: outside -> relevant pcl / inside->NOT relevant, like manholes reflection (extrusion is negative)
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> PointCloudThinner
Note: in case 1.500000 is reached simplify point cloud (LASground license limit). Set to 1.400000 to make space for ALS
PointCloudThinner
    MAX_NUM_POINTS = 1400000
    THINNED -> ALS_MLScombiner

Bookmark: 2.2.1: LASTools
Note: -not_airborne flag activated
LAStools.lasground
    FME_BASENAME = @Value(fme_basename)
    FME_DATASET = @Value(fme_dataset)
    HORIZONTALUNITS = " "
    ISOLATEDPOINTS = 5
    LASMERGE = Use lastools output
    LASTOOL = C:\MasterThesis\Workbenches\LASTools\LAStools\bin\lasground_new.exe
    LAS_TYPE = @Value(las_type)
    NOISESTEP_XY = 0.5
    NOISESTEP_Z = 0.5
    NONGROUNDCLASSIFICATION = " "
    TERRAIN = -wilderness
    VERTICALUNITS = " "
    GroundClassified -> UniqueClassSplit

Bookmark: 2.2.2: PointCloud Height Calculator
UniqueClassSplit: PointCloudSplitter
    OUTPUT_ATTR = _split_value
    SPLIT_BY_DISPLAY = classification
    SPLIT_TYPE = Unique
    SPLIT -> MeanMinHeightMLS
MeanMinHeightMLS: PointCloudStatisticsCalculator
    POINT_COMPONENTS = "z        MODE intensity        "
    -> CopyHeight
CopyHeight: AttributeCreator
    ATTR_TABLE = SET_TO HeightCopy = @Value(z.mode)
    -> PointCloudComponentRemover

Bookmark: 2.2.3: Remap classes
PointCloudComponentRemover
    COMPONENTS_TO_REMOVE = classification
    -> MapClasses
MapClasses: PointCloudComponentAdder
    COMPONENTS_TO_ADD = classification,Int8,"FME_CONDITIONAL:DEFAULT_VALUE'1'BOOL_OP;OR;COMPOSITE_TEST;1 OR 2;TEST @Value(_split_value) = 33;TEST @Value(_split_value) = 1'1'BOOL_OP;OR;COMPOSITE_TEST;1 OR 2;TEST @Value(_split_value) = 34;TEST @Value(_split_value) = 2'2'FME_NUM_CONDITIONS3___"
    -> GroundPointsRefineALSHeight

Bookmark: 2.2.4: Rectify Offset Of The ALS
GroundPointsRefineALSHeight: TestFilter
    DEFAULT_VALUE = <UNFILTERED>
    TEST_LIST = "BOOL_OP,OR,COMPOSITE_TEST,""""""1"""""",TEST_CLAUSE,TEST @Value(_split_value) = 34",MLS,"BOOL_OP,OR,COMPOSITE_TEST,""""""1"""""",TEST_CLAUSE,TEST @Value(_split_value) = 2",ALS
    MLS -> AttributeRenamer_2
    ALS -> AttributeRenamer
AttributeRenamer_2
    ATTR_TABLE = RENAME_SET_DEFAULT HeightCopy > MLSheight
    -> FeatureMerger_4 [SUPPLIER]
    -> PointCloudCombiner
AttributeRenamer
    ATTR_TABLE = RENAME_SET_DEFAULT HeightCopy > ALSheight
    -> FeatureMerger_4 [REQUESTOR]
FeatureMerger_4
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> MoveToZero
Note: The difference between MLS and ALS is because of geoid height difference. ALS is shifted by fixed number (46.5). Here, it is refined to mean value of MLS height
MoveToZero: Offsetter
    MODE = Cartesian Coordinate
    XOFF = 0
    YOFF = 0
    ZOFF = -@Value(ALSheight)
    OFFSET -> MoveToRefinedHeight
MoveToRefinedHeight: Offsetter
    MODE = Cartesian Coordinate
    XOFF = 0
    YOFF = 0
    ZOFF = @Value(MLSheight)
    OFFSET -> PointCloudCombiner
PointCloudCombiner
    ACCUM_ATTRS_NAME = Yes
    EXTRACT_RASTER_NODATA_NAME = No
    GROUP_BY = gml_id
    SPACING = 1.0
    -> AttributeRemover
AttributeRemover
    REMOVE_ATTRS = ALSheight,MLSheight,_overlaps,_split_value,minHeight,PointCloud,z.mean
    -> CenterPointExtractor
    -> LAS_writer [Split]

Bookmark: 2.3.1: Move to local crs
Note: normalize the point cloud before export / ATTENTION, not shifted to 0 but 1m below zero! Because of MeshLab reconstruction in 0,0,0
CenterPointExtractor
    CENTX = _inside_x
    CENTY = _inside_y
    EXTRACTIONMODE = CENTER
    -> PointCloudStatisticsCalculator_2
PointCloudStatisticsCalculator_2
    POINT_COMPONENTS = "z MIN        intensity        "
    -> ExpressionEvaluator
ExpressionEvaluator
    ACTION = Create New Attribute
    EXPRESSION = @sum(@Value(z.min),10)
    VAL_ATTR = ZminAnd1
    -> Offsetter
Offsetter
    MODE = Cartesian Coordinate
    XOFF = -@Value(_inside_x)
    YOFF = -@Value(_inside_y)
    ZOFF = -@Value(ZminAnd1)
    OFFSET -> CoordinateSystemRemover
    OFFSET -> GeometryRemover_3
GeometryRemover_3
    -> FeatureMerger_3 [SUPPLIER]
CoordinateSystemRemover
    -> FeatureWriter [Passed]

Bookmark: 2.3.2: Intermediate writers
FeatureWriter
    DATASET = $(tmpXYZ)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = space
    POINTCLOUDXYZ_WRITE_UTF8_BOM = yes
    TOTAL_FEATURES_WRITTEN_ATTR = _total_features_written
    SUMMARY -> MeshlabMXLparser
Note: LAS only for visual inspection
LAS_writer: FeatureWriter [off]
    DATASET = C:\MasterThesis\Processing\IntermediatePointCloud_1\Road_1
    DATASET_ATTR = _dataset
    FEATURE_TYPE_LIST_ATTR = _feature_type
    FORMAT = LAS
    LAS_COMPRESSION = None
    LAS_COMPUTE_STATISTICS_ON_ARCGIS_LAS_DATASET = No
    LAS_COORDINATE_SYSTEM_GRANULARITY = FEATURE
    LAS_DESTINATION_DATASETTYPE_VALIDATION = Yes
    LAS_VERSION = 1.2
    TOTAL_FEATURES_WRITTEN_ATTR = _total_features_written

Bookmark: 2.3.3: MeshLab integration
Note: MeshLab configuration file parser
MeshlabMXLparser: PythonCaller
    NEW_ATTRIBUTES = _dataset _total_features_written
    PYTHONSOURCE:
      import xml.etree.ElementTree as ET #xml parser
      from fmeobjects import (FMELogFile,
                              FME_WARN)#FME native logs


      FMELogFile().logMessageString("#--- The MXL parser has started: ---#", FME_WARN)
      tree = ET.parse(FME_MacroValues['XMLinput'])
      root = tree.getroot()


      def xmlChanger(feature):

          #Use dictionary index to accesss specific values

          #---------------------------------------------------------------#
          #---Access 'Screened Poisson'---#
          #---------------------------------------------------------------#

          #Set up value for the octree depth
          #default == 12
          octreeDepth = float(root[1][2].get('value')) #take deafult value
          userOctreeDepth = float(FME_MacroValues['userOctreeDepth']) #use input value from user
          strUOD = str(userOctreeDepth)

          #if a value from user is different from the default value then use the user value
          if userOctreeDepth == octreeDepth:
              FMELogFile().logMessageString(' -> Surface Reconstruction: Screened Poisson Octree Depth applied with default value 12')
          else:
              root[1][2].set('value', strUOD)
              FMELogFile().logMessageString(' -> Surface Reconstruction: Screened Poisson Octree Depth applied with value ' + strUOD)


          #---------------------------------------------------------------#
          #---Access 'Simplification: Quadric Edge Collapse Decimation'---#
          #---------------------------------------------------------------#

          #Set up desired number of faces in the end of the simplification process
          #Use it on your own risk! :) -> if this is not known go to the next step
          #default = 1160554
          targetFaceNr = float(root[2][0].get('value'))
          userTargetFaceNr = float(FME_MacroValues['userTargetFace'])
          uTFN = str(userTargetFaceNr)

          if targetFaceNr == userTargetFaceNr:
              FMELogFile().logMessageString(' -> Target number of faces same as default 1160554')
          elif 0 == userTargetFaceNr:
              FMELogFile().logMessageString(' -> Target number of faces NOT applied')
          else:
              root[2][0].set('value', uTFN)
              FMELogFile().logMessageString(' -> Target number of faces applied with value' + uTFN + 'only true if Percentage reduction set to 0')


          #Set up desired percentage of faces in the end of the simplification process
          #Easier for user to estimate only range (0..1)
          targetPerc = float(root[2][1].get('value'))
          userTargetPerc = float(FME_MacroValues['userTargetPerc'])
          uTP = str(userTargetPerc)

          if userTargetPerc == targetPerc:
              FMELogFile().logMessageString(' -> Percentage reduction (0..1) applied with default value')
          elif 0 == userTargetPerc:
              root[2][1].set('value', uTP)
              FMELogFile().logMessageString(' -> Percentage reduction (0..1) NOT applied')
          else:
              root[2][1].set('value', uTP)
              FMELogFile().logMessageString(' -> Percentage reduction (0..1) applied with value ' + uTP)


          #Set up some cleaning to the process, like erasing unreferenced vertices, bad faces, etc.
          #default = true
          #autoClean = bool(root[2][11].get('value'))
          userAutoClean = str(FME_MacroValues['autoClean'])

          if userAutoClean == 'true':
              FMELogFile().logMessageString(' -> Post-simplification cleaning applied')
          else:
              root[2][11].set('value', userAutoClean)
              FMELogFile().logMessageString(' -> Post-simplification cleaning NOT applied')

          #write new mlx
          tree.write(FME_MacroValues['XMLOutput'])

          FMELogFile().logMessageString("#--- The MXL was parsed successfully ---#", FME_WARN)
    PYTHONSYMBOL = xmlChanger
    -> ListExploder
Note: FeatureWriter outputs a single report feature / where list attribute keeps the name / of the temp LAS file
ListExploder
    ATTR_ACCUM_MODE = Prefix Incoming List
    INCOMING_PREFIX = _lastools_
    INDEX_ATTR = _element_index
    LIST_ATTR = _feature_type{}
    LIST_FOUND -> AttributeExposer
AttributeExposer
    ATTR_LIST = _lastools_name
    -> StringConcatenator
Note: Create command line attribute
AttributeCreator_4
    ATTR_LIST = meshlabserver_command_line,""$(meshlabserver)" -i "@Value(pointcloudXYZnames)" -o "@Value(surfaceOBJnames)" -s "$(XMLOutput)""
    -> MeshLabServerCaller
Note: Execute meshlabserver.exe
MeshLabServerCaller: SystemCaller
    ATTR = _exit_code
    CMD = @Value(meshlabserver_command_line)
    -> SuccessOrFailure
SuccessOrFailure: TestFilter
    DEFAULT_VALUE = Failure
    TEST_LIST = BOOL_OP,OR,COMPOSITE_TEST,<Unused>,TEST_CLAUSE,"TEST @Value(_exit_code) = 0",Success
    Success -> FeatureReader [INITIATOR]
    Failure -> Terminator
Note: read back reconstructed objects
FeatureReader
    ATTRS_TO_EXPOSE = fme_feature_type
    ATTR_ACCUM_MODE = Only Use Result
    COMBINE_GEOM = Use Result
    DATASET = @Value(surfaceOBJnames)
    FORMAT = OBJ
    INTERACT = <No Spatial Filter>
    OBJ_MERGE_MESH_PARTS = No
    OBJ_MOVE_TO_WORLD_COORDSYS = Yes
    OBJ_USE_SEARCH_ENVELOPE = NO
    OBJ_VARIABLE_FEATURE_TYPES = yes
    OUTPUT_FEATURES_DISPLAY = Schema and Data Features
    <OTHER> -> FeatureMerger_3 [REQUESTOR]
Terminator
    MESSAGE = Translation Terminated. Meshlabserver.exe wasn't executed successfully

Bookmark: get writing paths and file names
Note: point cloud .xyz paths
StringConcatenator
    ACTION = Create New Attribute
    PARM_LINE = fme_basicstring:16%1%22%4:@Value(_dataset)\@Value(_lastools_name).xyz
    VAL_ATTR = pointcloudXYZnames
    -> StringConcatenator_2
Note: reconstructed surface obj paths
StringConcatenator_2
    ACTION = Create New Attribute
    PARM_LINE = fme_basicstring:16%1%22%4:@Value(_dataset)\@Value(_lastools_name).obj
    VAL_ATTR = surfaceOBJnames
    -> AttributeCreator_4

Bookmark: 2.3.4: Reconstructed surface Road clipper to Road extent
Note: insert original CRS positions
FeatureMerger_3
    ATTR_ACCUM_MODE = Merge Supplier
    ATTR_CONFLICT_RES = Use Requestor
    IGNORE_NULLS = No
    JOIN_KEYS = @Value(fme_feature_type) @Value(gml_id) AUTO
    MERGE_TYPE = Attributes Only
    PROCESS_DUPS = NO
    REJECT_NULL_MISSING_KEYS = No
    SUPPLIERS_FIRST = No
    MERGED -> Offsetter_2
Note: raw extent geometry
Junction_11
    -> Clipper_2 [CLIPPER]
Clipper_2
    BOUNDARY_CASES = Treat as Inside
    CLEANING_TOLERANCE = Automatic
    CLIPPED_ATTR = _clipped
    CLIP_TYPE = Multiple Clippers
    GROUP_BY = gml_id
    LINES_AS_SEGMENTS = No
    MEASURE_TYPE = Continuous
    MISSING_VAL_MODE = Compute
    PRESERVE_CLIPPEE_EXTENTS = No
    VAL_SOURCE = Clippee Only
    INSIDE -> Aggregator_4

Bookmark: back to original CRS
Offsetter_2
    MODE = Cartesian Coordinate
    XOFF = @Value(_inside_x)
    YOFF = @Value(_inside_y)
    ZOFF = @Value(ZminAnd1)
    OFFSET -> CoordinateSystemSetter
CoordinateSystemSetter
    COORDSYS = EPSG:32632
    -> GeometryCoercer

Bookmark: prepare for clipper
GeometryCoercer
    GQUERY:
      for $geom in //geometry
      where $geom/count(parent::geometry) = 0
      return number($geom/@fme_id)
    KIND = fme_composite_surface
    COERCED -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer_2
GeometryCoercer_2
    GQUERY:
      for $geom in //geometry
      where $geom/count(parent::geometry) = 0
      return number($geom/@fme_id)
    KIND = fme_polygon
    COERCED -> Clipper_2 [CLIPPEE]

Bookmark: 2.4.1: Attributes setting
Note: Add apriori attributes / to corresponding features
Junction_14
    -> AddAprioriCityGMLAtt [SUPPLIER]
Note: Aggregate and count features (FeatureNr)
Aggregator_4
    ACCUM_ATTRS_NAME = Use Attributes From One Feature
    AGGREGATE_TYPE = Homogeneous Collection (If Possible)
    COUNT_ATTR = FeaturesNr
    GROUP_BY = gml_id
    MODE = Geometry - Assemble One Level
    SEP = ,
    AGGREGATE -> AddAprioriCityGMLAtt [REQUESTOR]
AddAprioriCityGMLAtt: FeatureMerger
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> DateTimeStamper

Bookmark: 2.4.2: Add date CityGML-like
DateTimeStamper
    DATETIME_ATTR = Timestamp
    STAMP_TYPE = date
    TIMEZONE = local
    -> DateTimeConverter
DateTimeConverter
    DATETIME_ATTR = Timestamp
    OUT_FORMAT = %Y-%m-%d
    PASSTHROUGH = NO
    REPAIR_INPUT = YES
    -> CityGMLGeometrySetter

Bookmark: 2.4.3: Set CityGML geometry, attr.
CityGMLGeometrySetter
    GEOM = lod2MultiSurface
    ROLE = cityObjectMember
    -> AttributeManager_3
AttributeManager_3
    ATTR_TABLE:
      REMOVE PosMH
      REMOVE Accuracy
      REMOVE LoD
      REMOVE topHeight
      REMOVE minHeight
      REMOVE _overlaps
      REMOVE RelPosHeight
      REMOVE RHeight
      REMOVE fme_basename
      REMOVE fme_dataset
      REMOVE _inside_x
      REMOVE _inside_y
      REMOVE z.min
      REMOVE ZminAnd1
      REMOVE _geometry_name
      REMOVE _part_number
      REMOVE _clipped
    -> Road (writer CITYGML_2)

Bookmark: 3.1: CityGML writer
Road (writer CITYGML_2)
    attributes: citygml_feature_role xml_char(200), gml_name xml_char(200), citygml_target_uri xml_char(200), citygml_feature_role_attr_name xml_char(200), citygml_feature_role_attr_val xml_char(200), gml_description xml_char(200), citygml_creationDate xml_char(200), citygml_terminationDate xml_char(200), externalReference{}.externalObject.name xml_char(200), externalReference{}.externalObject.uri xml_char(200), externalReference{}.informationSystem xml_char(200), citygml_generalizes_to{}.xlink_href xml_char(200), citygml_relative_to_terrain xml_char(200), citygml_relative_to_water xml_char(200), citygml_appearance{}.xlink_href xml_char(200), citygml_class xml_char(200), citygml_class_codeSpace xml_char(200), citygml_function{} xml_char(200), citygml_function{}.codeSpace xml_char(200), citygml_usage{} xml_char(200), citygml_usage{}.codeSpace xml_char(200), citygml_level_of_detail{} xml_char(200), opendrive_roadObject_dynamic xml_char(200), opendrive_roadObject_id xml_char(200), opendrive_roadObject_name xml_char(200), opendrive_roadObject_orientation xml_char(200), opendrive_roadObject_type xml_char(200), opendrive_road_id xml_char(200), opendrive_road_junction xml_char(200), opendrive_road_length xml_char(200),
      opendrive_road_rule xml_char(200), citygml_traffic_area{}.xlink_href xml_char(200), citygml_auxiliary_traffic_area{}.xlink_href xml_char(200), opendrive_laneSection_index xml_char(200), opendrive_laneSection_start xml_char(200), opendrive_lane_id xml_char(200), opendrive_lane_level xml_char(200), opendrive_lane_material_friction xml_char(200), opendrive_lane_material_roughness xml_char(200), opendrive_lane_material_surface xml_char(200), opendrive_lane_roadMark_color xml_char(200), opendrive_lane_roadMark_material xml_char(200), opendrive_lane_roadMark_type xml_char(200), opendrive_lane_roadMark_weight xml_char(200), opendrive_lane_speed_max xml_char(200), opendrive_lane_type xml_char(200), Timestamp xml_buffer, FeaturesNr xml_uint64, _fme_no_clipper xml_char(200), z.mode xml_real64

Bookmark: 2.1.3: Point cloud clipper
Note: MLS without rectification (only if param set to No)
Note: rectified MLS point cloud

Bookmark: 2.2: Ground Points Filtering
Note: 33 - non-ground (1) / 34 - ground (2)

FME custom transformer SurfaceNormalExtractor
Calculates surface normal vectors on Faces from the average of the existing surface vertex normals. If no vertex normals exist, they will be generated by a GeometryValidator.
Normals will be stored as the following traits on each Face:
surface_normal_x
surface_normal_y
surface_normal_z
The SurfaceNormalExtractor will work on Composite and MultiSurfaces as well, with no need to de-aggregate. Meshes will be automatically converted to Composite Surfaces.
**Input**
Source features
**Output**
Output features with calculated surface normals

Input (input)
    -> GeometryCoercer_2
Note: Convert other surface types / to faced based surface
GeometryCoercer_2
    GQUERY:
      for $geom in //geometry
      where $geom/@fme_geometry_type = 'IFMEMesh'
      or $geom/@fme_geometry_type = 'IFMERectangleFace'
      or $geom/@fme_geometry_type = 'IFMETriangleFan'
      or $geom/@fme_geometry_type = 'IFMETriangleStrip'
      return number($geom/@fme_id)
    KIND = fme_composite_surface
    COERCED -> GeometryValidator
    UNTOUCHED -> GeometryValidator
Note: Generate vertex / normals if needed
GeometryValidator
    ISSUE_ATTR_NAME = _surface_normal_issues
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Create Face ids
GeometryPropertySetter
    CNT_ATTR = _surface_normal_id
    DOMAIN = _surface_normal_id
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor
    SET -> GeometryPropertySetter_UNTOUCHED_-__TraitMerger_REQUESTOR
    UNTOUCHED -> GeometryPropertySetter_UNTOUCHED_-__TraitMerger_REQUESTOR
    <REJECTED> -> Junction
GeometryPropertySetter_UNTOUCHED_-__TraitMerger_REQUESTOR: Junction
    -> TraitMerger [REQUESTOR]
Note: Extract Faces
GeometryPartExtractor
    EXTRACTTYPE_PARAM = Extract
    GQUERY:
      for $geom in //geometry
      where $geom/@fme_geometry_type = 'IFMEFace'
      return number($geom/@fme_id)
    PROCESSED -> GeometryPropertyExtractor
Note: Extract Face ids
GeometryPropertyExtractor
    EXTRACTTYPE_PARAM = Traits
    PREFIX_EXTRACTED_TRAITS = No
    TRAIT_ATTR_LIST = _surface_normal_id,No
    EXTRACTED -> GeometryCoercer
    UNTOUCHED -> Junction_2
Note: Coerce to polygon / for measure extraction
GeometryCoercer
    GQUERY:
      for $geom in //geometry
      where $geom/count(parent::geometry) = 0
      return number($geom/@fme_id)
    KIND = fme_polygon
    COERCED -> MeasureExtractor
Note: Extract normal measures
MeasureExtractor
    GEOM_TYPE = Whole Area
    MEASURE_LIST = fme_vertex_normal_x
    MEASURE_NAME = fme_vertex_normal_x
    -> MeasureExtractor_2
    <REJECTED> -> Junction_3
MeasureExtractor_2
    GEOM_TYPE = Whole Area
    MEASURE_LIST = fme_vertex_normal_y
    MEASURE_NAME = fme_vertex_normal_y
    -> MeasureExtractor_3
    <REJECTED> -> Junction_3
MeasureExtractor_3
    GEOM_TYPE = Whole Area
    MEASURE_LIST = fme_vertex_normal_z
    MEASURE_NAME = fme_vertex_normal_z
    -> ListSummer
    <REJECTED> -> Junction_3
Note: Sum normal measures
ListSummer
    RESULT = _normal_sum_x
    SRC_LIST = fme_vertex_normal_x{}
    -> ListSummer_2
ListSummer_2
    RESULT = _normal_sum_y
    SRC_LIST = fme_vertex_normal_y{}
    -> ListSummer_3
ListSummer_3
    RESULT = _normal_sum_z
    SRC_LIST = fme_vertex_normal_z{}
    -> ListElementCounter
Note: Count normal measures
ListElementCounter
    CNT_ATTR = _normal_count_x
    LIST_NAME = fme_vertex_normal_x{}
    -> ListElementCounter_2
ListElementCounter_2
    CNT_ATTR = _normal_count_y
    LIST_NAME = fme_vertex_normal_y{}
    -> ListElementCounter_3
ListElementCounter_3
    CNT_ATTR = _normal_count_z
    LIST_NAME = fme_vertex_normal_z{}
    -> AttributeCreator
Note: Calculate surface normal / from average of vertex / normals
AttributeCreator
    ATTR_TABLE:
      SET_TO surface_normal_x = @Evaluate(@Value(_normal_sum_x)/@Value(_normal_count_x))
      SET_TO surface_normal_y = @Evaluate(@Value(_normal_sum_y)/@Value(_normal_count_y))
      SET_TO surface_normal_z = @Evaluate(@Value(_normal_sum_z)/@Value(_normal_count_z))
    -> GeometryPropertySetter_2
Note: Set surface normal as traits
GeometryPropertySetter_2
    OVERWRITE_CHOICE = Yes
    REMOVE_ATTRIBUTE = No
    SETTYPE_PARAM = Traits From Attributes
    SRC_ATTRS = surface_normal_x _surface_normal_id surface_normal_z surface_normal_y
    SET -> AttributeRemover
    <REJECTED> -> Junction_4
Note: Remove uneeded attributes
AttributeRemover
    LIST_ATTRS = _surface_normal_issues{} fme_vertex_normal_x{} fme_vertex_normal_y{} fme_vertex_normal_z{}
    REMOVE_ATTRS = _normal_sum_x,surface_normal_x,_normal_sum_y,_normal_count_x,_normal_sum_z,_surface_normal_id,surface_normal_z,surface_normal_y
    -> AttributeKeeper_2
AttributeKeeper_2
    -> TraitMerger [SUPPLIER]
Note: Merge normal traits on / Faces by Face id
TraitMerger
    ATTR_ACCUM_MODE = Merge Supplier
    ATTR_CONFLICT_RES = Use Requestor
    COMPONENTS_TO_JOIN = _surface_normal_id;_surface_normal_id
    REQUESTOR_TYPE = Trait
    R_GQUERY:
      for $geom in //geometry
      where $geom/@fme_geometry_type = 'IFMEFace'
      return number($geom/@fme_id)
    SUPPLIER_TYPE = Trait
    S_GQUERY:
      for $geom in //geometry
      where $geom/count(parent::geometry) = 0
      return number($geom/@fme_id)
    RESULT -> GeometryPropertyRemover
    UNTOUCHED -> GeometryPropertyRemover
Note: Remove Face id
GeometryPropertyRemover
    REGEX_FILTER = _surface_normal_id
    REMOVETYPE_PARAM = Traits
    REMOVE_ALL = No
    REMOVED -> AttributeRemover_2
    UNTOUCHED -> AttributeRemover_2
Note: Remove uneeded attributes
AttributeRemover_2
    LIST_ATTRS = _surface_normal_issues{}
    -> Output (output)
Output (output)
Junction
    -> Junction_2
Junction_2
    -> Junction_3
Junction_3
    -> Junction_4
Junction_4

FME custom transformer LAStools.lasground
LAStools.lasground is a wrapper transformer for lasground.exe, a tool from LAStools software suite (www.rapidlasso.com).
Safe Software does not ship LAStools suite and does not provide support for its components. With problem regarding the wrapper transformer contact support@safe.com.
lasground.exe is a tool for bare-earth extraction: it classifies the LiDAR points into ground points (class = 2) and non-ground points (class = 1).
    See lasground documentation for more details and available options:
https://www.cs.unc.edu/~isenburg/lastools/download/lasground_README.txt
Make sure LAStools software suite is installed.
Specify the path to lasground_new.exe.
Refer to https://www.cs.unc.edu/~isenburg/lastools/download/lasground_README.txt for more information.

Parameters:
- LASTOOL = C:\Program Files\LAStools\bin\lasground_new.exe   # Lasground_new.exe location
- TERRAIN = -city   # or hills,-nature%Towns or flats,-town%City or warehouses,-city%Metropolis,-metro Terrain type
- NONGROUNDCLASSIFICATION = -non_ground_unchanged
- HORIZONTALUNITS =   # Meters, %Feet,-feet Horizontal units
- VERTICALUNITS =   # Meters, %Feet,-elevation_feet Vertical units
- NOISESTEP_XY = 4   # Cell size in XY
- NOISESTEP_Z = 4   # Cell size along Z
- ISOLATEDPOINTS = 5   # Number of isolated points in 3x3x3 array of cells
- LASMERGE = Use lastools output   # "Use lastools output"%"Merge with the source" Lastools output handling (LAS components only)
- FME_BASENAME = @Value(fme_basename)   # Fme Basename
- FME_DATASET = @Value(fme_dataset)   # Fme Dataset
- LAS_TYPE = @Value(las_type)   # Las Type

PointCloud (input)
    -> TclCaller_2
FilenamePartExtractor
    DIRNAME_ATTR = _dirname
    DIRPATH_ATTR = _dirpath
    EXTENSION_ATTR = _extension
    FULLNAME_ATTR = _filename
    ROOTNAME_ATTR = _rootname
    SRC_ATTR = @Value(_lastools_temp_input)
    -> FMEFunctionCaller
Note: @ExtractPointCloudProperties(MODIFICATION_PROPERTIES) / Adds three attributes: / _source_format / _source_dataset / _modified / The last one allows to tell whether the LAS file was changed after reading
FMEFunctionCaller
    FUNC = @ExtractPointCloudProperties(MODIFICATION_PROPERTIES)
    -> AttributeExposer_2
AttributeExposer_2
    ATTR_LIST = _modified,_source_format
    -> TestFilter
    -> FeatureMerger_2 [SUPPLIER]
TestFilter
    DEFAULT_VALUE = No direct LAS processing
    TEST_LIST:
      BOOL_OP,AND,COMPOSITE_TEST,<Unused>,TEST_CLAUSE,"TEST @Value(_source_format) = LAS
      TEST @Value(_modified) = No",Direct LAS processing
    Direct LAS processing -> AttributeCreator_2
    Direct LAS processing -> PointCloudMerger [REQUESTOR]
    No direct LAS processing -> FeatureWriter [Output]
    No direct LAS processing -> FeatureMerger [REQUESTOR]
    No direct LAS processing -> PointCloudMerger [REQUESTOR]
Note: Save point clouds as LAS in temp folder
FeatureWriter
    DATASET = @Value(_dirpath)
    DATASET_ATTR = _dataset
    FEATURE_TYPE_LIST_ATTR = _feature_type
    FORMAT = LAS
    LAS_COMPRESSION = None
    LAS_COORDINATE_SYSTEM_GRANULARITY = FEATURE
    LAS_DESTINATION_DATASETTYPE_VALIDATION = Yes
    LAS_VERSION = 1.4
    TOTAL_FEATURES_WRITTEN_ATTR = _total_features_written
    WRITER_DIRECTIVES = VERSION,1.4,COMPRESSION,None,DESTINATION_DATASETTYPE_VALIDATION,Yes,COORDINATE_SYSTEM_GRANULARITY,FEATURE
    SUMMARY -> ListExploder
Note: FeatureWriter outputs a single report feature / where list attribute keeps the name of the temp LAS file
ListExploder
    ATTR_ACCUM_MODE = Prefix Incoming List
    INCOMING_PREFIX = _lastools_
    INDEX_ATTR = _element_index
    LIST_ATTR = _feature_type{}
    LIST_FOUND -> AttributeExposer
AttributeExposer
    ATTR_LIST = _lastools_name
    -> FeatureMerger [SUPPLIER]
Note: We need FileWriter to finish saving temp LAS files before sending command to LAStools. / This transformer guarantees this by waiting a summary feature
FeatureMerger
    ATTR_ACCUM_MODE = Merge Supplier
    ATTR_CONFLICT_RES = Use Requestor
    IGNORE_NULLS = No
    JOIN_KEYS = @Value(_rootname) @Value(_lastools_name) AUTO
    MERGE_TYPE = Attributes Only
    PROCESS_DUPS = No
    SUPPLIERS_FIRST = No
    MERGED -> AttributeCreator_2
Note: Create command line attribute
AttributeCreator_2
    ATTR_LIST = _lastools_command_line,"FME_CONDITIONAL:DEFAULT_VALUE'""$(LASTOOL)" -i "@Value(_lastools_temp_input)" -o "@Value(_lastools_temp_output)" $(TERRAIN) $(NONGROUNDCLASSIFICATION) $(HORIZONTALUNITS) $(VERTICALUNITS) -cores 16 -not_airborne"'BOOL_OP;AND;COMPOSITE_TEST;<Unused>;TEST @Value(_source_format) = LAS;TEST @Value(_modified) = No'""$(LASTOOL)" -i "@Value(fme_dataset)" -o "@Value(_lastools_temp_output)" $(TERRAIN) $(NONGROUNDCLASSIFICATION) $(HORIZONTALUNITS) $(VERTICALUNITS) -cores 16 -not_airborne"'FME_NUM_CONDITIONS2___"
    -> SystemCaller_2
Note: Execute lastools lasground
SystemCaller_2
    ATTR = _exit_code
    CMD = @Value(_lastools_command_line)
    -> TestFilter_2
Note: If lastools finished successfully, / pass features further, / otherwise, terminate the translation
TestFilter_2
    DEFAULT_VALUE = Failure
    TEST_LIST = BOOL_OP,OR,COMPOSITE_TEST,<Unused>,TEST_CLAUSE,"TEST @Value(_exit_code) = 0",Success
    Success -> FeatureReader [INITIATOR]
    Failure -> Terminator
Note: Read back features from temp folder with results
FeatureReader
    ATTRS_TO_EXPOSE = fme_feature_type
    ATTR_ACCUM_MODE = Merge Initiator and Result
    ATTR_CONFLICT_RES = Use Result
    COMBINE_GEOM = Use Result
    DATASET = @Value(_lastools_temp_output)
    FEATURETYPES_RADIO = FEATURETYPES
    FORMAT = LAS
    INTERACT = <No Spatial Filter>
    LAS_CLIP_TO_ENVELOPE = NO
    LAS_GROUP_BY_DATASET = Yes
    LAS_USE_SEARCH_ENVELOPE = NO
    OUTPUT_FEATURES_DISPLAY = Based on Connections
    <OTHER> -> TestFilter_3
TestFilter_3
    DEFAULT_VALUE = Use lastools output
    TEST_LIST = BOOL_OP,OR,COMPOSITE_TEST,<Unused>,TEST_CLAUSE,"TEST $(LASMERGE) = Merge with the source",Merge with the source
    Merge with the source -> PointCloudComponentKeeper
    Use lastools output -> FMEFunctionCaller_2
Note: Keep only added (modified) component
PointCloudComponentKeeper
    COMPONENTS_TO_KEEP = x,y,z,classification
    -> PointCloudMerger [SUPPLIER]
Note: Merge original point clouds with modified by XYZ. / Not very important for LAS files, / but may be very important for other point clouds / - this way we preserve their original components
PointCloudMerger
    COMPONENTS_TO_JOIN = x x y y z z
    GROUP_BY = _lastools_temp_output
    HANDLE_CONFLICT = Use Supplier
    MERGED -> FMEFunctionCaller_2
Note: Issue a command for the output point cloud to kill itself / once it is not needed
FMEFunctionCaller_2
    FUNC = @Geometry(DELETE_SOURCE_DATASET)
    -> SystemCaller_3
Note: Some files won't be deleted by @geometry function / Delete temp files. Each feature deletes its own files. / Adjust TCL path name to Windows by replacing / forward slash with backslash / del @ReplaceString(@Value(_lastools_temp_input),/,\) /Q
SystemCaller_3
    ATTR = _exit_code
    CMD = del "@ReplaceString(@Value(_lastools_temp_input),/,\)" /Q
    -> AttributeRemover_3
Note: Remove temp attributes / Keep temp_output for joining the original fme_basename
AttributeRemover_3
    REMOVE_ATTRS = _dirpath,_modified,fme_basename,_rootname,_filename,_lastools_count,_total_features_written,_dirname,_dataset,_element_index,las_type,_lastools_command_line,_lastools_name,_lastools_temp_input,_source_format,fme_feature_type,_exit_code,_extension
    -> FeatureMerger_2 [REQUESTOR]
Note: Merge to pass fme_basename to the output
FeatureMerger_2
    ATTR_ACCUM_MODE = Merge Supplier
    ATTR_CONFLICT_RES = Use Requestor
    IGNORE_NULLS = No
    JOIN_KEYS = @Value(_lastools_temp_output) @Value(_lastools_temp_output) AUTO
    MERGE_TYPE = Attributes Only
    PROCESS_DUPS = No
    SUPPLIERS_FIRST = No
    MERGED -> AttributeExposer_3
AttributeExposer_3
    ATTR_LIST = fme_feature_type,_source_dataset
    -> AttributeRemover_2
Note: Remove attributes
AttributeRemover_2
    REMOVE_ATTRS = _source_format,_modified,_source_dataset,_lastools_temp_input,_lastools_temp_output,_rootname,las_type,_dirpath,_extension,fme_feature_type,_filename,_dirname
    -> GroundClassified (output)
GroundClassified (output)
Terminator
    MESSAGE = Translation Terminated. lasground.exe wasn't executed successfully

Bookmark: Reserve names for intermediate files
Note: Reserve a name for temp input for LAStools
TclCaller_2
    TCLPROG = FME_TempFilename input .las
    VAL_ATTR = _lastools_temp_input
    -> TclCaller_3
Note: Reserve a name for temp output for LAStools
TclCaller_3
    TCLPROG = FME_TempFilename output .las
    VAL_ATTR = _lastools_temp_output
    -> FilenamePartExtractor
