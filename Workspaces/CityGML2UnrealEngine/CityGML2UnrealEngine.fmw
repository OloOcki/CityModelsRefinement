FME workspace CityGML2UnrealEngine.fmw
Title: CityGML2UnrealEngine
Description: General note:
    This is a implementation of the methodology presented in the thesis:
    "Semantic-based Geometry Refinement of 3D City Models for Testing Automated Driving"
    Study case:
    CityGML Buildings, BuildingParts and Roads
History: 09.08.2020,OlafWysocki,

Parameters:
- DestDataset_UDATASMITH = C:\MasterThesis\Visualisation\FINALVisualisation\unrealEngineinput\datasmith_all   # Destination UDATASMITH Directory
- SourceDataset_CITYGML = C:\MasterThesis\Visualisation\FINALVisualisation\raw\merged\building3dcityDB.gml   # Source CityGML File(s)
- SourceDataset_CITYGML_3 = C:\MasterThesis\Visualisation\FINALVisualisation\raw\merged\road.gml   # Source CityGML File(s)

Readers:
- CITYGML_1: CITYGML from $(SourceDataset_CITYGML)
- CITYGML_2: CITYGML from $(SourceDataset_CITYGML_3)

Writers:
- UDATASMITH_1: UDATASMITH to $(DestDataset_UDATASMITH)

Note: General note: / This is a implementation of the methodology presented in the thesis: / "Semantic-based Geometry Refinement of 3D City Models for Testing Automated Driving"
Note: Study case: / CityGML Buildings, BuildingParts and Roads

Bookmark: 1.1: CityGML Buildings
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, HasGeoRefined xml_buffer, opendrive_roadObject_dynamic xml_buffer, opendrive_roadObject_id xml_buffer, opendrive_roadObject_name xml_buffer, opendrive_roadObject_orientation xml_buffer, opendrive_roadObject_type xml_buffer, opendrive_road_id xml_buffer, opendrive_road_junction xml_buffer, opendrive_road_length xml_buffer, opendrive_road_rule xml_buffer
    -> Counter_3
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, FeaturesNr xml_buffer, Timestamp xml_buffer
    -> Counter_2

Bookmark: 2.1: Insert new attribute for raw building
Counter_3
    CNT_ATTR = _count
    DOMAIN = counter
    SCOPE = Local
    START = 0
    -> StringConcatenator_3
StringConcatenator_3
    ACTION = Create New Attribute
    PARM_LINE = fme_basicstring:13%14:Raw_Building_@Value(_count)
    VAL_ATTR = UnrealEngine_name
    -> Triangulator_2

Bookmark: 2.2: Insert new attribute for refined structures
Counter_2
    CNT_ATTR = _count
    DOMAIN = counter
    SCOPE = Local
    START = 0
    -> StringConcatenator_2
StringConcatenator_2
    ACTION = Create New Attribute
    PARM_LINE = fme_basicstring:17%14:Refined_Building_@Value(_count)
    VAL_ATTR = UnrealEngine_name
    -> Triangulator_2

Bookmark: 1.2: CityGML Roads
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
Road (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, FeaturesNr xml_buffer, Timestamp xml_buffer, opendrive_laneSection_index xml_buffer, opendrive_laneSection_start xml_buffer, opendrive_lane_id xml_buffer, opendrive_lane_level xml_buffer,
      opendrive_lane_material_friction xml_buffer, opendrive_lane_material_roughness xml_buffer, opendrive_lane_material_surface xml_buffer, opendrive_lane_roadMark_color xml_buffer, opendrive_lane_roadMark_material xml_buffer, opendrive_lane_roadMark_type xml_buffer, opendrive_lane_roadMark_weight xml_buffer, opendrive_lane_speed_max xml_buffer, opendrive_lane_type xml_buffer, opendrive_road_id xml_buffer, opendrive_road_junction xml_buffer, opendrive_road_length xml_buffer, opendrive_road_rule xml_buffer, z.mode xml_buffer
    -> Counter

Bookmark: 2.3: Insert new attribute for road
Counter
    CNT_ATTR = _count
    DOMAIN = counter
    SCOPE = Local
    START = 0
    -> StringConcatenator
StringConcatenator
    ACTION = Create New Attribute
    PARM_LINE = fme_basicstring:13%14:Refined_Road_@Value(_count)
    VAL_ATTR = UnrealEngine_name
    -> Triangulator_2

Bookmark: 2: SYSTEM
Note: UnrealEngine accepts triangulated features
Triangulator_2
    DEAGGREGATE_INPUT = Deaggregate
    TIN_SURFACE -> MeshMerger_2
Note: combine to one object per gml_id
MeshMerger_2
    ACCUM_INPUT_ATTRS = Use Attributes From One Feature
    GROUP_BY = gml_id
    MESH -> Layer000 (writer UDATASMITH_1)

Bookmark: 3.1 Unreal Engine datasmith writer
Layer000 (writer UDATASMITH_1)
    attributes: gml_id string, gml_parent_id string, citygml_target_uri string, citygml_feature_role string, citygml_feature_role_attr_name string, citygml_feature_role_attr_val string, gml_description string, gml_name string, citygml_creationDate string, citygml_terminationDate string, externalReference__.externalObject.name string, externalReference__.externalObject.uri string, externalReference__.informationSystem string, citygml_generalizes_to__.xlink_href string, citygml_relative_to_terrain string, citygml_relative_to_water string, citygml_appearance__.xlink_href string, citygml_class string, citygml_class_codeSpace string, citygml_function__ string, citygml_function__.codeSpace string, citygml_usage__ string, citygml_usage__.codeSpace string, citygml_year_of_construction string, citygml_year_of_demolition string, citygml_roof_type string, citygml_roof_type_codeSpace string, citygml_measured_height string, citygml_measured_height_units string, citygml_storeys_above_ground string,
      citygml_storeys_below_ground string, citygml_storey_heights_above_ground string, citygml_storey_heights_above_ground_units string, citygml_storey_heights_below_ground string, citygml_storey_heights_below_ground_units string, citygml_outer_building_installation__.xlink_href string, citygml_interior_building_installation__.xlink_href string, citygml_bounded_by__.xlink_href string, citygml_level_of_detail__ string, citygml_interior_room__.xlink_href string, citygml_consists_of_building_part__.xlink_href string, citygml_address__.xlink_href string, HasGeoRefined string, opendrive_roadObject_dynamic string, opendrive_roadObject_id string, opendrive_roadObject_name string, opendrive_roadObject_orientation string, opendrive_roadObject_type string, opendrive_road_id string, opendrive_road_junction string, opendrive_road_length string, opendrive_road_rule string, _count string, UnrealEngine_name string, FeaturesNr string, Timestamp string, citygml_traffic_area__.xlink_href string, citygml_auxiliary_traffic_area__.xlink_href string, opendrive_laneSection_index string, opendrive_laneSection_start string,
      opendrive_lane_id string, opendrive_lane_level string, opendrive_lane_material_friction string, opendrive_lane_material_roughness string, opendrive_lane_material_surface string, opendrive_lane_roadMark_color string, opendrive_lane_roadMark_material string, opendrive_lane_roadMark_type string, opendrive_lane_roadMark_weight string, opendrive_lane_speed_max string, opendrive_lane_type string, z.mode string
