FME workspace ManholesDetector.fmw
Title: ManholesDetector
Description: General note:
    This is a implementation of the methodology presented in the thesis:
    "Semantic-based Geometry Refinement of 3D City Models for Testing Automated Driving"
    Study case:
    Manholes Detector
History: 09.08.2020,OlafWysocki,

Parameters:
- DestDataset_GML_3 = C:\MasterThesis\Processing\semanticEnrichment\Road\testManholesCityGML30\roadsManholes.gml   # Destination Geography Markup Language (GML) File
- SourceDataset_CITYGML = C:\MasterThesis\Processing\semanticEnrichment\Road\test10Roads\10roads.gml   # Source CityGML File(s)
- SourceDataset_LAS = ""C:\MasterThesis\Processing\IntermediatePointCloud_1\Road_1\roads_LAS\UUID_0e94439b-16d8-4557-96bc-14deba8c9f3f.las" "C:\MasterThesis\Processing\IntermediatePointCloud_1\Road_1\roads_LAS\UUID_0f0bd309-54f0-48bd-8dee-59ac669ce3cc.las" "C:\MasterThesis\Processing\IntermediatePointCloud_1\Road_1\roads_LAS\UUID_0f3c7d0d-c83d-4d6f-b3f2-2d72863dd894.las" "C:\MasterThesis\Processing\IntermediatePointCloud_1\Road_1\roads_LAS\UUID_1b9b4528-9e34-432d-8f3d-d29552a47504.las" "C:\MasterThesis\Processing\IntermediatePointCloud_1\Road_1\roads_LAS\UUID_1b114bd3-a17c-463b-a909-a2cf91e623f5.las" "C:\MasterThesis\Processing\IntermediatePointCloud_1\Road_1\roads_LAS\UUID_1c5d0e82-c2c2-4d1a-b0a5-fe7f03a7828f.las" "C:\MasterThesis\Processing\IntermediatePointCloud_1\Road_1\roads_LAS\UUID_1c91ad7b-ab73-4275-9c43-0e524e231817.las" "C:\MasterThesis\Processing\IntermediatePointCloud_1\Road_1\roads_LAS\UUID_1e7be77b-d688-46f6-89b5-d57bb245f771.las" "C:\MasterThesis\Processing\IntermediatePointCloud_1\Road_1\roads_LAS\UUID_1e13f821-f85d-485c-8b9f-00b03b47bee5.las" "C:\MasterThesis\Processing\IntermediatePointCloud_1\Road_1\roads_LAS\UUID_1f7a3e9b-3cf8-4065-a7a2-cc2b7c3bfbce.las" "C:\MasterThesis\Processing\IntermediatePointCloud_1\Road_1\roads_LAS\UUID_1fad1e90-a57c-4f70-b6de-27b1d300ccf7.las" "C:\MasterThesis\Processing\IntermediatePointCloud_1\Road_1\roads_LAS\UUID_3c911069-91e1-4493-bb31-e30e136047f6.las" "C:\MasterThesis\Processing\IntermediatePointCloud_1\Road_1\roads_LAS\UUID_3d737214-37dd-4246-b85c-f06490f72a99.las" "C:\MasterThesis\Processing\IntermediatePointCloud_1\Road_1\roads_LAS\UUID_3e618b16-ee22-4567-8c4d-8b2475f5159e.las" "C:\MasterThesis\Processing\IntermediatePointCloud_1\Road_1\roads_LAS\UUID_4ce3bc7c-09f7-40bd-a399-b6e17ba918b7.las" "C:\MasterThesis\Processing\IntermediatePointCloud_1\Road_1\roads_LAS\UUID_4d82cbcc-9d89-4bf3-a210-1ee7a940f203.las" "C:\MasterThesis\Processing\IntermediatePointCloud_1\Road_1\roads_LAS\UUID_4e565af2-2578-46b0-8165-76357c72f3a5.las" "C:\MasterThesis\Processing\IntermediatePointCloud_1\Road_1\roads_LAS\UUID_5d1b526d-4067-4021-b374-8161b3136ca0.las" "C:\MasterThesis\Processing\IntermediatePointCloud_1\Road_1\roads_LAS\UUID_6a79cced-01c4-4308-9098-153e32df5c9a.las" "C:\MasterThesis\Processing\IntermediatePointCloud_1\Road_1\roads_LAS\UUID_6c7bf709-3e91-4651-8dc3-d82af8a10650.las" "C:\MasterThesis\Processing\IntermediatePointCloud_1\Road_1\roads_LAS\UUID_6fb39a14-8ee9-4def-9b2a-23229921005f.las" "C:\MasterThesis\Processing\IntermediatePointCloud_1\Road_1\roads_LAS\UUID_07d6efa2-4824-4e26-8da5-71f307dc23cd.las" "C:\MasterThesis\Processing\IntermediatePointCloud_1\Road_1\roads_LAS\UUID_7ad92b49-0841-411e-8091-e17791be57dd.las" "C:\MasterThesis\Processing\IntermediatePointCloud_1\Road_1\roads_LAS\UUID_7d860405-69b1-4add-b575-991f7c70d8ed.las" "C:\MasterThesis\Processing\IntermediatePointCloud_1\Road_1\roads_LAS\UUID_7e3e9e61-9b08-4cc2-8155-9376eeb6be67.las" "C:\MasterThesis\Processing\IntermediatePointCloud_1\Road_1\roads_LAS\UUID_8c54b966-6231-415c-9370-424fc52e545b.las" "C:\MasterThesis\Processing\IntermediatePointCloud_1\Road_1\roads_LAS\UUID_8ee530ff-ffd9-49d8-912b-b2cd5168590a.las" "C:\MasterThesis\Processing\IntermediatePointCloud_1\Road_1\roads_LAS\UUID_8ff36a79-81de-40f9-a66c-cc7767d4498e.las" "C:\MasterThesis\Processing\IntermediatePointCloud_1\Road_1\roads_LAS\UUID_09af531b-b361-4249-9ee1-42db81873e17.las" "C:\MasterThesis\Processing\IntermediatePointCloud_1\Road_1\roads_LAS\UUID_9b1d1eb0-04cc-4b23-9cdc-ecb2c3e84565.las" "C:\MasterThesis\Processing\IntermediatePointCloud_1\Road_1\roads_LAS\UUID_9e6ac536-9bff-434d-8d66-b06f3f3894d7.las" "C:\MasterThesis\Processing\IntermediatePointCloud_1\Road_1\roads_LAS\UUID_9f837c36-fc17-4b94-b071-7c8fdf2f7f77.las" "C:\MasterThesis\Processing\IntermediatePointCloud_1\Road_1\roads_LAS\UUID_16a4705b-2879-47cb-81e9-a2738eab8014.las" "C:\MasterThesis\Processing\IntermediatePointCloud_1\Road_1\roads_LAS\UUID_16fd2d5d-c0ce-4b0e-8c14-4058b8cae3e8.las" "C:\MasterThesis\Processing\IntermediatePointCloud_1\Road_1\roads_LAS\UUID_25f800f9-e9f6-41e1-94a6-efd494dfaff3.las" "C:\MasterThesis\Processing\IntermediatePointCloud_1\Road_1\roads_LAS\UUID_26d40218-1f56-4a16-b4aa-60c885ad2bc0.las" "C:\MasterThesis\Processing\IntermediatePointCloud_1\Road_1\roads_LAS\UUID_44b68d14-abcd-401c-ac42-8c509aaf3c51.las" "C:\MasterThesis\Processing\IntermediatePointCloud_1\Road_1\roads_LAS\UUID_55df1ed3-2385-453c-813f-0cdbce441dc7.las" "C:\MasterThesis\Processing\IntermediatePointCloud_1\Road_1\roads_LAS\UUID_64eb56f9-9b52-4e61-83f9-61ad819335bd.las" "C:\MasterThesis\Processing\IntermediatePointCloud_1\Road_1\roads_LAS\UUID_65f01fdb-1000-4689-87cc-ad0130866a5b.las" "C:\MasterThesis\Processing\IntermediatePointCloud_1\Road_1\roads_LAS\UUID_71ba6120-8e3c-44fa-8c39-40569a0c0547.las" "C:\MasterThesis\Processing\IntermediatePointCloud_1\Road_1\roads_LAS\UUID_74cd074e-6b78-4f46-9353-3440483b9806.las" "C:\MasterThesis\Processing\IntermediatePointCloud_1\Road_1\roads_LAS\UUID_84ebceba-ee20-47f8-b4d4-ce52fd6bcd10.las" "C:\MasterThesis\Processing\IntermediatePointCloud_1\Road_1\roads_LAS\UUID_96e0f533-b532-40af-80d4-77ba4fe3c995.las" "C:\MasterThesis\Processing\IntermediatePointCloud_1\Road_1\roads_LAS\UUID_419e56c8-dbf7-4e99-b139-4e04678e96f9.las" "C:\MasterThesis\Processing\IntermediatePointCloud_1\Road_1\roads_LAS\UUID_427d330d-6a48-462f-9060-bb47ad3a80bb.las" "C:\MasterThesis\Processing\IntermediatePointCloud_1\Road_1\roads_LAS\UUID_479c9e9b-4e67-49b1-bbfd-162e992b1345.las" "C:\MasterThesis\Processing\IntermediatePointCloud_1\Road_1\roads_LAS\UUID_660fcd1c-963d-41e8-a9b7-973bd6399b48.las" "C:\MasterThesis\Processing\IntermediatePointCloud_1\Road_1\roads_LAS\UUID_997f52bf-b62f-43df-b80d-1e8d3eb93936.las" "C:\MasterThesis\Processing\IntermediatePointCloud_1\Road_1\roads_LAS\UUID_3404e45a-f7ec-4485-bf05-662b11d2f3bf.las" "C:\MasterThesis\Processing\IntermediatePointCloud_1\Road_1\roads_LAS\UUID_3897e333-1d26-46bd-b17c-4bf7916fac9b.las" "C:\MasterThesis\Processing\IntermediatePointCloud_1\Road_1\roads_LAS\UUID_6111e432-c067-4b8f-813a-79cebf6bfbf2.las" "C:\MasterThesis\Processing\IntermediatePointCloud_1\Road_1\roads_LAS\UUID_21775c1c-121b-4411-a244-f0b9ccb7d385.las" "C:\MasterThesis\Processing\IntermediatePointCloud_1\Road_1\roads_LAS\UUID_40386c95-6d43-45b0-92ec-6cb42f7359d6.las" "C:\MasterThesis\Processing\IntermediatePointCloud_1\Road_1\roads_LAS\UUID_00169051-b723-4166-a281-9692cea48c54.las" "C:\MasterThesis\Processing\IntermediatePointCloud_1\Road_1\roads_LAS\UUID_271307dc-3605-4314-aa2d-ffb1b31b5b11.las" "C:\MasterThesis\Processing\IntermediatePointCloud_1\Road_1\roads_LAS\UUID_445287ad-9944-4b09-9a74-31439724e703.las" "C:\MasterThesis\Processing\IntermediatePointCloud_1\Road_1\roads_LAS\UUID_677825b5-ca93-4660-a40b-8dd99bd689f5.las" "C:\MasterThesis\Processing\IntermediatePointCloud_1\Road_1\roads_LAS\UUID_764257a4-d27d-40f6-8c13-f8f8c6d84912.las" "C:\MasterThesis\Processing\IntermediatePointCloud_1\Road_1\roads_LAS\UUID_5848571f-6acd-4b30-a2f0-adbee18d6878.las" "C:\MasterThesis\Processing\IntermediatePointCloud_1\Road_1\roads_LAS\UUID_57796863-98fd-4fed-aa1c-98198afccb2d.las" "C:\MasterThesis\Processing\IntermediatePointCloud_1\Road_1\roads_LAS\UUID_92828729-0c22-409f-971a-6c61ae4b4433.las" "C:\MasterThesis\Processing\IntermediatePointCloud_1\Road_1\roads_LAS\UUID_a5dee055-ac85-4900-afcd-6a7e27d93356.las" "C:\MasterThesis\Processing\IntermediatePointCloud_1\Road_1\roads_LAS\UUID_aa2a210a-54f0-47db-8372-90c053ac8d1c.las" "C:\MasterThesis\Processing\IntermediatePointCloud_1\Road_1\roads_LAS\UUID_abdf45d2-fc5a-4e16-b6de-5caa61023c16.las" "C:\MasterThesis\Processing\IntermediatePointCloud_1\Road_1\roads_LAS\UUID_adf41ef9-c8d6-4fb3-9460-ecefbb4f36e1.las" "C:\MasterThesis\Processing\IntermediatePointCloud_1\Road_1\roads_LAS\UUID_b018b12a-6292-42a6-b5a7-a6a1f66f9686.las" "C:\MasterThesis\Processing\IntermediatePointCloud_1\Road_1\roads_LAS\UUID_b42e90ea-746e-41b6-bc14-5cb0be85111f.las" "C:\MasterThesis\Processing\IntermediatePointCloud_1\Road_1\roads_LAS\UUID_b61d9a23-ea31-451c-ab22-98b2509e4905.las" "C:\MasterThesis\Processing\IntermediatePointCloud_1\Road_1\roads_LAS\UUID_b84ec188-2a8d-4971-accb-e5c414e80efc.las" "C:\MasterThesis\Processing\IntermediatePointCloud_1\Road_1\roads_LAS\UUID_b854cf00-f1eb-44b1-bf1a-3e20a9fcac76.las" "C:\MasterThesis\Processing\IntermediatePointCloud_1\Road_1\roads_LAS\UUID_b969e8c5-3f70-4323-9fb2-d1b8909923b5.las" "C:\MasterThesis\Processing\IntermediatePointCloud_1\Road_1\roads_LAS\UUID_beb46444-9ede-43f9-9cd2-a4981980467e.las" "C:\MasterThesis\Processing\IntermediatePointCloud_1\Road_1\roads_LAS\UUID_bec4325e-2200-44d7-9c25-c6645cad0934.las" "C:\MasterThesis\Processing\IntermediatePointCloud_1\Road_1\roads_LAS\UUID_bf15a469-9c2b-45be-8032-3b2d2960b864.las" "C:\MasterThesis\Processing\IntermediatePointCloud_1\Road_1\roads_LAS\UUID_c1a7c32d-b219-4f03-8ad3-3351e7a63cf8.las" "C:\MasterThesis\Processing\IntermediatePointCloud_1\Road_1\roads_LAS\UUID_c762f254-ab48-4d6c-a1a9-838866c1e713.las" "C:\MasterThesis\Processing\IntermediatePointCloud_1\Road_1\roads_LAS\UUID_cb59a097-8ebe-41a6-b67e-658b4323ef27.las" "C:\MasterThesis\Processing\IntermediatePointCloud_1\Road_1\roads_LAS\UUID_cda1ef14-ea19-4bae-82ac-1fa433899fbe.las" "C:\MasterThesis\Processing\IntermediatePointCloud_1\Road_1\roads_LAS\UUID_d28ed9ef-1cba-4bd1-a3a5-e755d9170f1e.las" "C:\MasterThesis\Processing\IntermediatePointCloud_1\Road_1\roads_LAS\UUID_d77a2404-2f46-44dc-8284-19658222918a.las" "C:\MasterThesis\Processing\IntermediatePointCloud_1\Road_1\roads_LAS\UUID_d7586ea5-3ed9-46e4-afea-ccde15c13e6f.las" "C:\MasterThesis\Processing\IntermediatePointCloud_1\Road_1\roads_LAS\UUID_d7816214-b149-416c-aeb6-0eda35bb9ab7.las" "C:\MasterThesis\Processing\IntermediatePointCloud_1\Road_1\roads_LAS\UUID_d9898253-79a3-4df7-80bf-d4aa9d1ec09d.las" "C:\MasterThesis\Processing\IntermediatePointCloud_1\Road_1\roads_LAS\UUID_da4ee645-ef3a-45be-9a70-4e5567ce6463.las" "C:\MasterThesis\Processing\IntermediatePointCloud_1\Road_1\roads_LAS\UUID_dbbdc207-b062-44c4-a680-2003f13039ec.las" "C:\MasterThesis\Processing\IntermediatePointCloud_1\Road_1\roads_LAS\UUID_dd23fe76-d0b4-4759-962f-2e12024d77e3.las" "C:\MasterThesis\Processing\IntermediatePointCloud_1\Road_1\roads_LAS\UUID_e1e0df87-8a99-413b-b848-f56d97722ce8.las" "C:\MasterThesis\Processing\IntermediatePointCloud_1\Road_1\roads_LAS\UUID_e3ae747a-cac3-46db-9358-b408fee8238a.las" "C:\MasterThesis\Processing\IntermediatePointCloud_1\Road_1\roads_LAS\UUID_e37bfb2f-f991-4a9f-aa46-ca23fccd3fe0.las" "C:\MasterThesis\Processing\IntermediatePointCloud_1\Road_1\roads_LAS\UUID_e93b7772-3d5c-427c-9da7-5f88bf913da6.las" "C:\MasterThesis\Processing\IntermediatePointCloud_1\Road_1\roads_LAS\UUID_ec3dc956-a868-4030-8194-6b46f90f2af2.las" "C:\MasterThesis\Processing\IntermediatePointCloud_1\Road_1\roads_LAS\UUID_ee92257c-012a-44df-8c33-e5800a43d74b.las" "C:\MasterThesis\Processing\IntermediatePointCloud_1\Road_1\roads_LAS\UUID_f0cd0e23-aef4-4cb7-af54-344e7612b098.las" "C:\MasterThesis\Processing\IntermediatePointCloud_1\Road_1\roads_LAS\UUID_f44d6857-96cc-4bb1-8706-63da640981b0.las" "C:\MasterThesis\Processing\IntermediatePointCloud_1\Road_1\roads_LAS\UUID_f58ff8f5-482e-4a7a-ac2d-79c31c310fd5.las" "C:\MasterThesis\Processing\IntermediatePointCloud_1\Road_1\roads_LAS\UUID_f0057545-8244-41b9-94eb-36d4e2420966.las" "C:\MasterThesis\Processing\IntermediatePointCloud_1\Road_1\roads_LAS\UUID_fca27a4b-9788-4aea-8d82-72f72845e026.las" "C:\MasterThesis\Processing\IntermediatePointCloud_1\Road_1\roads_LAS\UUID_fe49e804-8c7b-4fd3-8c85-168a34ed1b5d.las""   # Source ASPRS LAS File(s)

Readers:
- CITYGML_1: CITYGML from $(SourceDataset_CITYGML)
- LAS_1: LAS from $(SourceDataset_LAS)

Writers:
- GML_1: GML to $(DestDataset_GML_3)

Note: General note: / This is a implementation of the methodology presented in the thesis: / "Semantic-based Geometry Refinement of 3D City Models for Testing Automated Driving"
Note: Study case: / Manholes Detector
Note: More about CityGML 3.0 implementation (also XSDs): / https://github.com/tum-gis/citygml3.0-transportation-examples

Bookmark: 1.1: Refined CityGML model
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> Junction_3
Note: to writer CityModel
Junction_3
    -> Junction_4
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, FeaturesNr xml_buffer, Timestamp xml_buffer, opendrive_laneSection_index xml_buffer, opendrive_laneSection_start xml_buffer, opendrive_lane_id xml_buffer, opendrive_lane_level xml_buffer,
      opendrive_lane_material_friction xml_buffer, opendrive_lane_material_roughness xml_buffer, opendrive_lane_material_surface xml_buffer, opendrive_lane_roadMark_color xml_buffer, opendrive_lane_roadMark_material xml_buffer, opendrive_lane_roadMark_type xml_buffer, opendrive_lane_roadMark_weight xml_buffer, opendrive_lane_speed_max xml_buffer, opendrive_lane_type xml_buffer, opendrive_road_id xml_buffer, opendrive_road_length xml_buffer, opendrive_road_rule xml_buffer
    -> CoordinateSystemSetter_2
CoordinateSystemSetter_2
    COORDSYS = EPSG:32632
    -> TestFilter_3 [off]
    -> 2DForcer
    -> Junction

Bookmark: 2.4: CityGML 3.0 preparation
Note: from raw CityModel
Junction_4
    -> AttributeCreator_2
Note: raw road
Junction_6
    -> AttributeKeeper

Bookmark: 2.4.1: CityModel
AttributeCreator_2
    ATTR_TABLE:
      SET_TO gml_id = CityModel
      SET_TO gml_name = CityGML3_Transportation_simpleIntersection_granularity_way
    -> CityModel (writer GML_1)

Bookmark: 3.1: CityGML 3.0
CityModel (writer GML_1)
    attributes: gml_name xml_buffer, citygml_target_uri xml_buffer, gml_description xml_buffer, citygml_city_object_member{}.xlink_href xml_buffer, citygml_appearance_member{}.xlink_href xml_buffer, gml_feature_member{}.xlink_href xml_buffer
Road (writer GML_1)
    attributes: citygml_feature_role xml_char(200), citygml_lod_name xml_char(200), gml_name xml_char(200)
Hole (writer GML_1)
    attributes: citygml_feature_role xml_char(200), gml_name xml_char(200)
HoleSurface (writer GML_1)
    attributes: citygml_feature_role xml_char(200), citygml_lod_name xml_char(200), gml_name xml_char(200), lod3MultiSurface xml_char(200)

Bookmark: 2.1: Preprocessing
Note: enforce 2.5D cut
2DForcer
    2D -> Clipper [CLIPPER]
Note: to manhole clipper
Junction
    -> Junction_2
    -> Junction_5
Note: to CityGML 3.0 writer
Junction_5
    -> Junction_6
Clipper
    BOUNDARY_CASES = Treat as Inside
    CLEANING_TOLERANCE = Automatic
    CLIPPED_ATTR = _clipped
    CLIP_TYPE = Multiple Clippers
    GROUP_BY = gml_id
    LINES_AS_SEGMENTS = No
    MEASURE_TYPE = Continuous
    MISSING_VAL_MODE = Compute
    PRESERVE_CLIPPEE_EXTENTS = No
    VAL_SOURCE = Clippee Only
    INSIDE -> AttributeRenamer

Bookmark: 2.2: Possible testing...
Note: test for roads with manholes
TestFilter_3 [off]
    DEFAULT_VALUE = <UNFILTERED>
    TEST_LIST = "BOOL_OP,OR,COMPOSITE_TEST,""""""1"""""",TEST_CLAUSE,TEST @Value(gml_id) = UUID_dd23fe76-d0b4-4759-962f-2e12024d77e3",randomWithManhole,"BOOL_OP,OR,COMPOSITE_TEST,""""""1"""""",TEST_CLAUSE,TEST @Value(gml_id) = UUID_e3ae747a-cac3-46db-9358-b408fee8238a",gate,"BOOL_OP,OR,COMPOSITE_TEST,""""""1"""""",TEST_CLAUSE,TEST @Value(gml_id) = UUID_660fcd1c-963d-41e8-a9b7-973bd6399b48",byGarage,"BOOL_OP,OR,COMPOSITE_TEST,""""""1"""""",TEST_CLAUSE,TEST @Value(gml_id) = UUID_b018b12a-6292-42a6-b5a7-a6a1f66f9686",byTheRedBld,"BOOL_OP,OR,COMPOSITE_TEST,""""""1"""""",TEST_CLAUSE,TEST @Value(gml_id) = UUID_92828729-0c22-409f-971a-6c61ae4b4433",byCrossroadsBld
    gate -> Junction [off]
Note: test for roads with manholes
TestFilter [off]
    DEFAULT_VALUE = <UNFILTERED>
    TEST_LIST = "BOOL_OP,OR,COMPOSITE_TEST,""""""1"""""",TEST_CLAUSE,TEST @Value(gml_id) = UUID_dd23fe76-d0b4-4759-962f-2e12024d77e3",randomWithManhole,"BOOL_OP,OR,COMPOSITE_TEST,""""""1"""""",TEST_CLAUSE,TEST @Value(gml_id) = UUID_e3ae747a-cac3-46db-9358-b408fee8238a",gate,"BOOL_OP,OR,COMPOSITE_TEST,""""""1"""""",TEST_CLAUSE,TEST @Value(gml_id) = UUID_660fcd1c-963d-41e8-a9b7-973bd6399b48",byGarage,"BOOL_OP,OR,COMPOSITE_TEST,""""""1"""""",TEST_CLAUSE,TEST @Value(gml_id) = UUID_b018b12a-6292-42a6-b5a7-a6a1f66f9686",byTheRedBld,"BOOL_OP,OR,COMPOSITE_TEST,""""""1"""""",TEST_CLAUSE,TEST @Value(gml_id) = UUID_92828729-0c22-409f-971a-6c61ae4b4433",byCrossroadsBld
    randomWithManhole -> Clipper [CLIPPEE] [off]

Bookmark: 2.4.2: Road
AttributeKeeper
    KEEP_ATTRS = gml_id
    -> AttributeCreator
AttributeCreator
    ATTR_TABLE:
      SET_TO gml_parent_id = CityModel
      SET_TO citygml_feature_role = Road
      SET_TO citygml_lod_name = lod3MultiSurface
      SET_TO gml_name = OpenDRIVE
    -> Road (writer GML_1)

Bookmark: 2.3: Add manhole to CityGML Road model
Note: from refined CityGML Road
Junction_2
    -> GeometryCoercer_2
Note: clipp out the manhole
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Aggregator_2
Aggregator_2
    ACCUM_ATTRS_NAME = Use Attributes From One Feature
    AGGREGATE_TYPE = Homogeneous Collection (If Possible)
    GROUP_BY = road_id
    MODE = Geometry - Assemble One Level
    SEP = ,
    AGGREGATE -> StringConcatenator_2

Bookmark: 2.3.1: Prepare for clipper
GeometryCoercer_2
    GQUERY:
      for $geom in //geometry
      where $geom/count(parent::geometry) = 0
      return number($geom/@fme_id)
    KIND = fme_composite_surface
    COERCED -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer_3
GeometryCoercer_3
    GQUERY:
      for $geom in //geometry
      where $geom/count(parent::geometry) = 0
      return number($geom/@fme_id)
    KIND = fme_polygon
    COERCED -> Clipper_3 [CLIPPEE]

Bookmark: 1.2: MLS point cloud
LAS (reader LAS_1)
    -> AttributeRenamer_2
Note: fileName as gml_id
AttributeRenamer_2
    ATTR_TABLE = RENAME_SET_DEFAULT fme_basename > gml_id
    -> CoordinateSystemSetter_8
Note: Attention / -> valid MLS point cloud saved in an intermediate step of the "RoadsRefinement" workspace (go there to section "2.3.2: Intermediate writers", the LAS_writer transformer) / -> Also there, manholes corrections have to be turn ON
CoordinateSystemSetter_8
    COORDSYS = EPSG:32632
    -> TestFilter [off]
    -> Clipper [CLIPPEE]

Bookmark: 2.2.1: Rescale intensity values
AttributeRenamer
    ATTR_TABLE = RENAME_SET_DEFAULT gml_id > road_id
    -> PointCloudCoercer
PointCloudCoercer
    ACCUM_ATTRS_NAME = Yes
    CONVERT_TO_DISPLAY = Individual Points
    PART_NUMBER_ATTR_NAME = _part_number
    POINT_COMPONENTS = intensity
    POINT_COMPONENTS_PRESERVE_DISPLAY = Attributes
    COERCED -> ExpressionEvaluator
Note: rescale to 1800 - 32800
ExpressionEvaluator
    ACTION = Create New Attribute
    EXPRESSION = @mult(@div(@sub(@Value(intensity),0), @sub(254,0)),@sub(32800,18000)) + 18000
    VAL_ATTR = _result
    -> AttributeManager
Note: set new intensity
AttributeManager
    ATTR_TABLE:
      REMOVE _clipped
      REMOVE intensity
      REMOVE _part_number
      RENAME_SET_VALUE _result > intensity
    -> PointCloudCombiner
PointCloudCombiner
    ACCUM_ATTRS_NAME = Yes
    ATTRS_TO_PRESERVE = intensity,Real64
    EXTRACT_RASTER_NODATA_NAME = No
    GROUP_BY = road_id
    SPACING = 1.0
    -> PointCloudSplitter_2

Bookmark: 2.2.2: Apply threshold
PointCloudSplitter_2
    OUTPUT_ATTR = _split_value
    RANGE_LIST = 26000,27200,metal roof,28400,29200,stucco building,,,
    SPLIT_BY_DISPLAY = intensity
    SPLIT_TYPE = Range
    SPLIT -> PointCloudSeperator_2
PointCloudSeperator_2: TestFilter
    DEFAULT_VALUE = other
    TEST_LIST = "BOOL_OP,OR,COMPOSITE_TEST,""""""1"""""",TEST_CLAUSE,TEST @Value(_split_value) = stucco building",stucco building
    stucco building -> PointCloudCombiner_2

Bookmark: 2.2.3: Filter out noise
Note: merge possible manholes point clouds
PointCloudCombiner_2
    ACCUM_ATTRS_NAME = Yes
    EXTRACT_RASTER_NODATA_NAME = No
    GROUP_BY = road_id
    SPACING = 1.0
    -> PointCloudDensityCalculator_2 [PointCloud]
    -> BoundingBoxReplacer
BoundingBoxReplacer
    BOXTYPE = 2D Oriented Bounding Box
    BOX -> Clipper_4 [CLIPPER]
Note: find most dense areas -> probable manholes
PointCloudDensityCalculator_2
    PIXELSIZE = 0.1
    DensityRaster -> Clipper_4 [CLIPPEE]
Note: separate raster per input road and add id again
Clipper_4
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterCellCoercer_2

Bookmark: 2.2.3.1: Find a manhole based on manhole national norms
RasterCellCoercer_2
    CELL_GEOMETRY = Points
    EXTRACT_BAND_VALUES_AS = Attributes
    EXTRACT_NODATA = No
    PRESERVE_ATTRIBUTES = Yes
    -> ListExploder_2
Note: density per point as attribute
ListExploder_2
    ATTR_ACCUM_MODE = Merge List Attributes
    ATTR_CONFLICT_RES = Use List Attribute Values
    INDEX_ATTR = _element_index
    LIST_ATTR = _band{}
    ELEMENTS -> StatisticsCalculator
Note: CALCULATE most dense region
StatisticsCalculator
    CALCULATION_MODE = NUMERIC
    FEAT_STATS = value,,MAX,,,,,,,,,,
    GROUP_BY = road_id
    COMPLETE -> TestFilter_4
    COMPLETE -> Sorter

Bookmark: Select top dense patches
Sorter
    GROUP_BY = road_id
    SORT_PARM = value NUMERIC DESCENDING
    SORTED -> Counter
Counter
    CNT_ATTR = _count
    DOMAIN = @Value(road_id)
    SCOPE = Local
    START = 1
    -> TestFilter_2
TestFilter_2
    DEFAULT_VALUE = <UNFILTERED>
    TEST_LIST = "BOOL_OP,OR,COMPOSITE_TEST,""""""1"""""",TEST_CLAUSE,TEST @Value(_count) <= 10",<=10 most dense patches
    <=10 most dense patches -> Bufferer_3

Bookmark: check overlap between patches
Bufferer_3
    ANGLE = 22.5
    CAP_STYLE = Arc
    CORNER_STYLE = Arc
    MODE = AREA
    OFFSET = 0.2
    OFFSET_UNITS = NONE
    PRECISION = APPROX
    BUFFERED -> AreaOnAreaOverlayer [AREA]
Note: how many overlaps
AreaOnAreaOverlayer
    ACCUM_ATTRS_NAME = Use Attributes From One Feature
    CLEANING_TOLERANCE = Automatic
    CONNECT_Z_MODE = First Wins
    DEAGGREGATE_INPUT = Yes
    GROUP_BY = road_id
    OVC_ATTR = _overlaps
    AREA -> Counter_2

Bookmark: 2.2.3.1.1: Find the most dense area within patches
Note: tmp count to check vs. filtered out features and terminate the workspace
Counter_2
    CNT_ATTR = _tmpCount2
    DOMAIN = @Value(road_id)
    SCOPE = Local
    START = 1
    -> TestFilter_5

Bookmark: most overlaping region as seed point
TestFilter_5
    DEFAULT_VALUE = No manhole found!
    TEST_LIST = "BOOL_OP,OR,COMPOSITE_TEST,""""""1"""""",TEST_CLAUSE,TEST @Value(_overlaps) >= 5",>=5 overlaps
    >=5 overlaps -> StatisticsCalculator_2
Note: CALCULATE most overlapping region
StatisticsCalculator_2
    CALCULATION_MODE = NUMERIC
    FEAT_STATS = _overlaps,,MAX,,,,,,,,,,
    GROUP_BY = road_id
    COMPLETE -> Tester_2

Bookmark: only most overlapping points passed further
Note: only most overlapping points region
Tester_2
    BOOL_OP = OR
    COMPOSITE_TEST = 1
    TEST_CLAUSE = TEST @Value(_overlaps.max) = @Value(_overlaps)
    TEST_MODE = TEST
    PASSED -> Counter_4
Counter_4
    CNT_ATTR = mostOverlapCount
    DOMAIN = @Value(road_id)
    SCOPE = Local
    START = 1
    -> StatisticsCalculator_3
StatisticsCalculator_3
    CALCULATION_MODE = NUMERIC
    FEAT_STATS = mostOverlapCount,,MAX,,,,,,,,,,
    GROUP_BY = road_id
    COMPLETE -> PassOnlyIfOneOverlap
PassOnlyIfOneOverlap: Tester
    BOOL_OP = OR
    COMPOSITE_TEST = 1
    TEST_CLAUSE = TEST @Value(mostOverlapCount.max) = 1
    TEST_MODE = TEST
    PASSED -> CenterPointReplacer_2
    FAILED -> PassOnlyIfOneOverlap_Failed
Note: log segments with no manholes found
PassOnlyIfOneOverlap_Failed: Logger
    LOG_FEATURE = LOG_ONLY
    MAXCOORDS = 20
    MAXFEATS = 20
    MESSAGE = Within those segments no manhole was found:  @Value(road_id)
    SEVERITY = WARN

Bookmark: Only seed point
CenterPointReplacer_2
    POINTTYPE = CENTEROFGRAV
    POINT -> MarkAsSeedPoint
MarkAsSeedPoint: AttributeCreator
    ATTR_TABLE = SET_TO markAsSeedPoint = 1
    -> AttributeKeeper_4
AttributeKeeper_4
    KEEP_ATTRS = road_id,markAsSeedPoint
    -> TestFilter_4
    -> AttributeKeeper_4_Output
AttributeKeeper_4_Output: Inspector

Bookmark: 2.2.3.1.2: Include possible deviations for found seed point
TestFilter_4
    DEFAULT_VALUE = RestOfPoints
    TEST_LIST = "BOOL_OP,OR,COMPOSITE_TEST,""""""1"""""",TEST_CLAUSE,TEST @Value(markAsSeedPoint) = 1",ManholeSeed
    ManholeSeed -> Bufferer
    ManholeSeed -> Clipper_2 [CLIPPEE]
    RestOfPoints -> Clipper_2 [CLIPPEE]
Note: seed could be in any place within succo part of the manhole. This part has 480mm diameter / Thus: / one can create "safe" buffer of diameter of the whole manhole according to DIN + diameter of the succo part + error of a patch
Bufferer
    ANGLE = 22.5
    CAP_STYLE = Arc
    CORNER_STYLE = Arc
    MODE = AREA
    OFFSET = @div(0.785,2) + @div(0.480,2) + 0.1
    OFFSET_UNITS = METERS
    PRECISION = APPROX
    BUFFERED -> Clipper_2 [CLIPPER]
Clipper_2
    BOUNDARY_CASES = Treat as Inside
    CLEANING_TOLERANCE = Automatic
    CLIPPED_ATTR = _clipped
    CLIP_TYPE = Multiple Clippers
    GROUP_BY = road_id
    LINES_AS_SEGMENTS = No
    MEASURE_TYPE = Continuous
    MISSING_VAL_MODE = Compute
    PRESERVE_CLIPPEE_EXTENTS = No
    VAL_SOURCE = Clippee Only
    INSIDE -> ChartGenerator_2
    INSIDE -> DensityThreshold_2
Note: in case of visual inspection
Note: filter out outliers
DensityThreshold_2: TestFilter
    DEFAULT_VALUE = probableManhole
    TEST_LIST = "BOOL_OP,OR,COMPOSITE_TEST,""""""1"""""",TEST_CLAUSE,TEST @Value(value) < 10",<10 density
    probableManhole -> Aggregator

Bookmark: histogram
Note: plot histogram (in case of visual inspection)
ChartGenerator_2 [off]
    AXES_FONT = Arial,12
    AXES_LW = 0.5
    BACKGROUND_COLOR = 1,1,1
    CHART_SETUP = SUMMARY_DATA;value;NUM_BINS;3;COLOR;0,0,1;TREND_LINE;NO;FME_CONTROLLER_QUERY_FILE;transformers/dependencies/charter/Histogram.fme
    CHART_TYPE = Histogram
    DPI = 300
    INTERPRETATION = RGBA32
    LEGEND = A
    LEGEND_FONT = Arial,6
    LEGEND_OPTIONS = YES
    TICKS = T
    TICK_FONT = Arial,10
    TITLE_FONT = Arial,12
    X_INCH = 2.0
    X_LOG = LIN
    Y_INCH = 2.0
    Y_LOG = LIN

Bookmark: 2.2.3.1.3: Manhole range
Aggregator
    ACCUM_ATTRS_NAME = Use Attributes From One Feature
    AGGREGATE_TYPE = Homogeneous Collection (If Possible)
    GROUP_BY = road_id
    MODE = Geometry - Assemble One Level
    SEP = ,
    AGGREGATE -> CenterPointReplacer
Note: find the center of gravity
CenterPointReplacer
    POINTTYPE = CENTER
    POINT -> Bufferer_2
Note: diameter of the whole manhole according to DIN
Bufferer_2
    ANGLE = 22.5
    CAP_STYLE = Arc
    CORNER_STYLE = Arc
    MODE = AREA
    OFFSET = @div(0.785,2)
    OFFSET_UNITS = NONE
    PRECISION = APPROX
    BUFFERED -> Clipper_3 [CLIPPER]

Bookmark: 2.3.2 Attributes for Hole
StringConcatenator_2
    ACTION = Create New Attribute
    PARM_LINE = fme_basicstring:15%1%1:@Value(road_id)_h
    VAL_ATTR = gml_id
    -> AttributeKeeper_5
AttributeKeeper_5
    KEEP_ATTRS = gml_id
    -> GeometryRemover
    -> AttributeCreator_6

Bookmark: 2.4.3: Hole (NO geometry)
GeometryRemover
    -> AttributeCreator_4
AttributeCreator_4
    ATTR_TABLE:
      SET_TO gml_parent_id = CityModel
      SET_TO citygml_feature_role = Hole
      SET_TO gml_name = Hole
    -> Hole (writer GML_1)

Bookmark: 2.4.4: HoleSurface (geometry)
Note: gml_parent_id
AttributeCreator_6
    ATTR_TABLE = SET_TO gml_parent_id = @Value(gml_id)
    -> UUIDGenerator
Note: uniqueId
UUIDGenerator
    UUID_ATTR = gml_id
    -> AttributeCreator_5
AttributeCreator_5
    ATTR_TABLE:
      SET_TO citygml_feature_role = SurfaceHole
      SET_TO citygml_lod_name = lod3MultiSurface
      SET_TO gml_name = surfaceHole
    -> GeometryExtractor
Note: set gml compliant geometry
GeometryExtractor
    ATTR = lod3MultiSurface
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> GeometryPropertySetter
GeometryPropertySetter
    OVERWRITE_CHOICE = Yes
    REMOVE_ATTRIBUTE = No
    SETTYPE_PARAM = Traits From Attributes
    SRC_ATTRS = citygml_lod_name
    SET -> HoleSurface (writer GML_1)

Bookmark: 3: OUTPUT
Address (writer GML_1) [off]
    attributes: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
AuxiliaryTrafficArea (writer GML_1) [off]
    attributes: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
AuxiliaryTrafficSpace (writer GML_1) [off]
    attributes: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
ClearanceSpace (writer GML_1) [off]
    attributes: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
ClosureSurface (writer GML_1) [off]
    attributes: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
Intersection (writer GML_1) [off]
    attributes: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
Marking (writer GML_1) [off]
    attributes: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
Railway (writer GML_1) [off]
    attributes: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
Section (writer GML_1) [off]
    attributes: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
Square (writer GML_1) [off]
    attributes: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
Track (writer GML_1) [off]
    attributes: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
TrafficArea (writer GML_1) [off]
    attributes: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
TrafficSpace (writer GML_1) [off]
    attributes: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
Waterway (writer GML_1) [off]
    attributes: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
